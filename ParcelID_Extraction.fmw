FME workspace ParcelID_Extraction.fmw

Parameters:
- SourceTXT = \\10.10.30.59\gis\Parcel Handling\Data\LEGDAT.txt   # Source Text File
- SDESCECD = SCECD SDE   # FAMILY:Esri ArcSDE Geodatabase SDE Connction to SCECD
- SourceDataset_GEODATABASE_SDE = SCECD SDE   # ArcSDE Geodatabase Connection

Readers:
- TEXTLINE_1: TEXTLINE from $(SourceTXT)
- GEODATABASE_SDE_1: GEODATABASE_SDE from $(SDESCECD)
- GEODATABASE_SDE_3: GEODATABASE_SDE from $(SourceDataset_GEODATABASE_SDE)

Writers:
- GEODATABASE_SDE_2: GEODATABASE_SDE to SCECD SDE

Note: Import both parcel GIS files and the LEGDAT text file provided by the assessor's office. Prep the data from both sources, and then do a match based on a common attribute (parcel ID), then override existing subd names from the GIS parcels with the ones sent in the text file (more accurate)
Note: Import source data. Looking for comma delimited text file sent by the assessor's office
text_line (reader TEXTLINE_1)
    attributes: text_line_data buffer
    -> Subd_Name_Replacement
Note: Finds erratic strings in subdivision names and replaces them with standardized versions. / Example: / PHS 1 --> PHASE 1
Subd_Name_Replacement: Subd Name Replacement
    TEXT_LINE_DATA = @Value(text_line_data)
    -> Subd_Name_Cleaners
Note: Then use regex expressions to remove unnecessary parts of subdivision names. / Example: / PHASE 1 --> [nothing]
Subd_Name_Cleaners: Subd Name Cleaners
    TEXT_LINE_DATA = @Value(text_line_data)
    _PARCELID = @Value(_ParcelID)
    _SUBDNAME = @Value(_SubdName)
    -> Title_Case
Note: Finally, convert subdivision names to Full Title Case
Title_Case: Title Case
    _SUBDNAME = @Value(_SubdName)
    -> Join_Parcels [RIGHT]
Note: Import parcels from SQL
SHELBY/Parcels (reader GEODATABASE_SDE_1)
    attributes: OBJECTID integer, gcUnqID char(38), srcOfData char(75), srcLastEdt date, uploadAuth char(75), uploadDate date, effective date, expire date, srcUnqID char(100), parOwn char(150), parOwn2 char(150), parOwnAdd char(150), parOwnTel char(15), parAdd char(150), parNum integer, parStreet char(100), parType char(100), extResrce char(254), comments char(100), gcModDate date, gcModType char(2), gcEditBy char(100), gcException char(75), gcLabel char(150), Shape.STArea() double, Shape.STLength() double
    -> Prep_Source_Parcels
Note: Remove extra spaces
Prep_Source_Parcels: Prep Source Parcels
    COMMENTS = @Value(comments)
    EFFECTIVE = @Value(effective)
    EXPIRE = @Value(expire)
    EXTRESRCE = @Value(extResrce)
    GCEDITBY = @Value(gcEditBy)
    GCEXCEPTION = @Value(gcException)
    GCLABEL = @Value(gcLabel)
    GCMODDATE = @Value(gcModDate)
    GCMODTYPE = @Value(gcModType)
    GCUNQID = @Value(gcUnqID)
    OBJECTID = @Value(OBJECTID)
    PARADD = @Value(parAdd)
    PARNUM = @Value(parNum)
    PAROWN = @Value(parOwn)
    PAROWN2 = @Value(parOwn2)
    PAROWNADD = @Value(parOwnAdd)
    PAROWNTEL = @Value(parOwnTel)
    PARSTREET = @Value(parStreet)
    PARTYPE = @Value(parType)
    SHAPE.STAREA__ = @Value(Shape.STArea())
    SHAPE.STLENGTH__ = @Value(Shape.STLength())
    SRCLASTEDT = @Value(srcLastEdt)
    SRCOFDATA = @Value(srcOfData)
    SRCUNQID = @Value(srcUnqID)
    UPLOADAUTH = @Value(uploadAuth)
    UPLOADDATE = @Value(uploadDate)
    -> Join_Parcels [LEFT]
Join_Parcels: FeatureJoiner
    ATTR_CONFLICT_RES = Prefer Left
    GEOMETRY_HANDLING = Prefer Left
    JOIN_KEYS = psrcUnqID _ParcelID AUTO
    JOIN_MODE = Inner
    JOINED -> Override_Subd_Name
    UNJOINED_LEFT -> Override_Subd_Name_2
Note: 1:1 match found. Proceed to override subd name (Label) with the one from the text file
Override_Subd_Name: AttributeCreator
    ATTR_TABLE = SET_TO pgcLabel (varchar(200)) = @Value(_SubdName)
    -> Junction_3
Override_Subd_Name_2: AttributeCreator
    ATTR_TABLE = SET_TO pgcLabel (buffer) = FME_NULL_VALUE
    -> Junction_3
Note: Parcel ID C0243 00656 is not making it through. It's not getting joined
Note: parAddress needs to be populated / Assign a weighted metrix based on the structure type field with the value 1 = house being the highest
Junction_3
    -> AttributeManager
Note: Organize and rename fields as needed
AttributeManager
    ATTR_TABLE:
      RENAME_SET_VALUE pOBJECTID > OBJECTID (int32)
      RENAME_SET_VALUE _ParcelID > ParcelID (varchar(100))
      RENAME_SET_VALUE _SubdName > SubdName (varchar(200))
      RENAME_SET_VALUE psrcOfData > Source (varchar(75))
      RENAME_SET_VALUE psrcLastEdt > EditDate (datetime)
      RENAME_SET_VALUE puploadAuth > UploadAuth (varchar(75))
      RENAME_SET_VALUE puploadDate > UploadDate (datetime)
      RENAME_SET_VALUE peffective > Effective (datetime)
      RENAME_SET_VALUE pexpire > Expire (datetime)
      RENAME_SET_VALUE pparOwn > ParOwn (varchar(150))
      RENAME_SET_VALUE pparOwn2 > ParOwn2 (varchar(150))
      RENAME_SET_VALUE pparOwnAdd > ParOwn3 (varchar(150))
      RENAME_SET_VALUE pparOwnTel > ParOwnTel (varchar(15))
      RENAME_SET_VALUE pparAdd > ParAddress (varchar(150))
      RENAME_SET_VALUE pparNum > ParStNum (int32)
      RENAME_SET_VALUE pparStreet > ParStName (varchar(100))
      RENAME_SET_VALUE pparType > ParStType (varchar(100))
      RENAME_SET_VALUE pextResrce > ExtResrce (varchar(254))
      RENAME_SET_VALUE pcomments > Comments (varchar(100))
      REMOVE psrcUnqID (varchar(100))
      REMOVE pgcModDate (datetime)
      REMOVE pgcLabel (varchar(200))
      REMOVE pgcUnqID (varchar(38))
      REMOVE pgcModType (varchar(2))
      REMOVE pgcEditBy (varchar(100))
      REMOVE pgcException (varchar(75))
      REMOVE text_line_data (buffer)
      REMOVE _ParcelInfo{} (varchar(200))
      REMOVE _element_count (uint64)
    -> Filter_Out_Invalid
Note: If any parcels come through with no parcel ID, exclude them, otherwise, procceed to the writer
Filter_Out_Invalid: Tester
    BOOL_OP = COMPOSITE
    COMPOSITE_TEST = NOT ( 1 OR 2 OR 3 OR 4 OR 5 )
    TEST_CLAUSE:
      TEST ParcelID ATTRIBUTE_VALUE_NULL ""
      TEST ParcelID ATTRIBUTE_IS_EMPTY ""
      TEST ParcelID ATTRIBUTE_IS_MISSING ""
      TEST @Value(ParcelID) =
      TEST @Value(ParcelID) =
    TEST_MODE = TEST
    PASSED -> Parcels_Curated (writer GEODATABASE_SDE_2)
Parcels_Curated (writer GEODATABASE_SDE_2)
    attributes: OBJECTID integer, ParcelID char(200), SubdName char(200), Source char(75), EditDate date, UploadAuth char(75), UploadDate date, Effective date, Expire date, ParOwn char(150), ParOwn2 char(150), ParOwn3 char(150), ParOwnTel char(15), ParAddress char(150), ParStNum integer, ParStName char(100), ParStType char(100), ExtResrce char(254), Comments char(100), pShape_STArea__ double, pShape_STLength__ double
Note: Aggregate and dissolve for better performance in the clipper
Aggregator [off]
    ACCUM_ATTRS_NAME = Drop Incoming Attributes
    AGGREGATE_TYPE = Homogeneous Collection (If Possible)
    GROUP_BY = psrcUnqID
    MODE = Geometry - Assemble One Level
    SEP = ,
Dissolver [off]
    ACCUM_INPUT_ATTRS = Use Attributes From One Feature
    CLEANING_TOLERANCE = Automatic
    CONNECT_Z_MODE = First Wins
    DEAGGREGATE_INPUT = Yes
    GROUP_BY = psrcUnqID
SHELBY/Parcels_Curated (reader GEODATABASE_SDE_3) [off]
    attributes: OBJECTID integer, Shape.STArea() double, Shape.STLength() double

FME custom transformer Title Case

Parameters:
- _SUBDNAME = @Value(_SubdName)   # Subdname

Input (input)
    -> Change_to_Title
Note: Change _SubdName to Full Title Case
Change_to_Title: StringCaseChanger
    ATTRCHOICE = Selected Attributes
    ATTRLIST = _SubdName
    CHANGE_TYPE = Full Title Case
    -> Find_MC
Note: Note: this is not by any means an exhaustive list of exceptions. Add more as needed
Output (output)

Bookmark: Mc Scenarios
Note: Do a regex search for MC[A-Z] to find examples like McFarlin
Note: If not found, continue...
Find_MC: Tester
    BOOL_OP = OR
    TEST_CLAUSE = CASE_INSENSITIVE_TEST @Value(_SubdName) CONTAINS_REGEX MC[A-Z]
    TEST_MODE = CASE_INSENSITIVE_TEST
    PASSED -> Replace_Mc
    FAILED -> Junction
Note: Replace Mc with ~~~ / This is done because those characters are guaranteed to not be used legitimately in the data. This way we can find these later and replace them with Mc again
Replace_Mc: StringReplacer
    CASE = NO
    FIND_TEXT = Mc
    NO_MATCH = _FME_NO_OP_
    REGEXP = NO
    REPLACE_TEXT = ~~~
    SRC_ATTRS = _SubdName
    -> Split_Title_Case
Note: Change to newly split strings to title case
Split_Title_Case: StringCaseChanger
    ATTRCHOICE = Selected Attributes
    ATTRLIST = _SubdName
    CHANGE_TYPE = Full Title Case
    -> Replace_wth_Mc
Note: Replace ~~~ with Mc again
Replace_wth_Mc: StringReplacer
    CASE = NO
    FIND_TEXT = ~~~
    NO_MATCH = _FME_NO_OP_
    REGEXP = NO
    REPLACE_TEXT = Mc
    SRC_ATTRS = _SubdName
    -> MixedCase_Exceptions
Junction
    -> MixedCase_Exceptions

Bookmark: Notable Exceptions
Note: Search for each individually
MixedCase_Exceptions: TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_SubdName) CONTAINS_REGEX YMCA",YMCA,"BOOL_OP,OR,COMPOSITE_TEST,""""""1"""""",TEST_CLAUSE,CASE_INSENSITIVE_TEST @Value(_SubdName) CONTAINS_REGEX (^USA | USA | USA$)",USA,"BOOL_OP,OR,COMPOSITE_TEST,""""""1"""""",TEST_CLAUSE,CASE_INSENSITIVE_TEST @Value(_SubdName) CONTAINS_REGEX (^TN | TN | TN$)",TN
    YMCA -> YMCA
    USA -> USA
    TN -> TN
    <UNFILTERED> -> Output (output)
Note: Then replace with the exception
YMCA: StringReplacer
    CASE = NO
    FIND_TEXT = YMCA
    NO_MATCH = _FME_NO_OP_
    REGEXP = YES
    REPLACE_TEXT = YMCA
    SRC_ATTRS = _SubdName
    -> Junction_2
USA: StringReplacer
    CASE = NO
    FIND_TEXT = (^USA | USA | USA$)
    NO_MATCH = _FME_NO_OP_
    REGEXP = YES
    REPLACE_TEXT = USA
    SRC_ATTRS = _SubdName
    -> Junction_2
TN: StringReplacer
    CASE = NO
    FIND_TEXT = (^TN | TN | TN$)
    NO_MATCH = _FME_NO_OP_
    REGEXP = YES
    REPLACE_TEXT = TN
    SRC_ATTRS = _SubdName
    -> Junction_2
Junction_2
    -> Output (output)

FME custom transformer Prep Source Parcels

Parameters:
- COMMENTS = @Value(comments)   # comments
- EFFECTIVE = @Value(effective)   # effective
- EXPIRE = @Value(expire)   # expire
- EXTRESRCE = @Value(extResrce)   # extResrce
- GCEDITBY = @Value(gcEditBy)   # gcEditBy
- GCEXCEPTION = @Value(gcException)   # gcException
- GCLABEL = @Value(gcLabel)   # gcLabel
- GCMODDATE = @Value(gcModDate)   # gcModDate
- GCMODTYPE = @Value(gcModType)   # gcModType
- GCUNQID = @Value(gcUnqID)   # gcUnqID
- OBJECTID = @Value(OBJECTID)
- PARADD = @Value(parAdd)   # parAdd
- PARNUM = @Value(parNum)   # parNum
- PAROWN = @Value(parOwn)   # parOwn
- PAROWN2 = @Value(parOwn2)   # parOwn2
- PAROWNADD = @Value(parOwnAdd)   # parOwnAdd
- PAROWNTEL = @Value(parOwnTel)   # parOwnTel
- PARSTREET = @Value(parStreet)   # parStreet
- PARTYPE = @Value(parType)   # parType
- SHAPE.STAREA__ = @Value(Shape.STArea())   # Shape.STArea()
- SHAPE.STLENGTH__ = @Value(Shape.STLength())   # Shape.STLength()
- SRCLASTEDT = @Value(srcLastEdt)   # srcLastEdt
- SRCOFDATA = @Value(srcOfData)   # srcOfData
- SRCUNQID = @Value(srcUnqID)   # srcUnqID
- UPLOADAUTH = @Value(uploadAuth)   # uploadAuth
- UPLOADDATE = @Value(uploadDate)   # uploadDate

Note: Reproject to state plane if needed
Reproject_Parcels: EsriReprojector [off]
    DEST = ESRIWKT|NAD_1983_StatePlane_Tennessee_FIPS_4100_Feet|PROJCS["NAD_1983_StatePlane_Tennessee_FIPS_4100_Feet",GEOGCS["GCS_North_American_1983",DATUM["D_North_American_1983",SPHEROID["GRS_1980",6378137.0,298.257222101]],PRIMEM["Greenwich",0.0],UNIT["Degree",0.0174532925199433]],PROJECTION["Lambert_Conformal_Conic"],PARAMETER["False_Easting",1968500.0],PARAMETER["False_Northing",0.0],PARAMETER["Central_Meridian",-86.0],PARAMETER["Standard_Parallel_1",35.25],PARAMETER["Standard_Parallel_2",36.41666666666666],PARAMETER["Latitude_Of_Origin",34.33333333333334],UNIT["Foot_US",0.3048006096012192]]
    GEOTRANSFORMATION_NAME = WGS_1984_(ITRF00)_To_NAD_1983
    INTERPOLATION_TYPE_NAME = Nearest Neighbor
    RASTER_CELL_SIZE = Preserve Cells
    RASTER_TOLERANCE = 0.0
    SOURCE = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
Input (input)
    -> Rename_Parcels
Note: Rename incoming fields to make it clear where they are coming from
Rename_Parcels: BulkAttributeRenamer
    ATTRCHOICE = All Attributes
    MODE_CHOICE = RENAME
    PATTERN_ACTION_DISP = ADDPREFIX
    REPLACE_STR = p
    -> Replace_Double_Spaces
Spaces_Loop (input)
    -> Replace_Double_Spaces
Note: Reduce double spaces to single spaces
Replace_Double_Spaces: StringReplacer
    CASE = NO
    FIND_TEXT = "  "
    NO_MATCH = _FME_NO_OP_
    REGEXP = YES
    REPLACE_TEXT = " "
    SRC_ATTRS = psrcUnqID
    -> Check_Spaces_Again
Note: Check to see if any other spaces were found. / Send back if found. Else continue...
Check_Spaces_Again: Tester
    BOOL_OP = OR
    TEST_CLAUSE = CASE_SENSITIVE_TEST @Value(psrcUnqID) CONTAINS_REGEX
    TEST_MODE = TEST
    PASSED -> Spaces_Loop (output)
    FAILED -> Timmer_Ends
Note: Do a trim on the ends
Timmer_Ends: AttributeTrimmer
    SRC_ATTRS = psrcUnqID
    TRIM_CHARS = " "
    TRIM_TO_NONE = Yes
    TRIM_TYPE = Both
    -> Output (output)
Output (output)
Spaces_Loop (output)

FME custom transformer Subd Name Replacement

Parameters:
- TEXT_LINE_DATA = @Value(text_line_data)   # Text Line Data

Note: Incoming from the very end if internal double spaces are found. This way, logic can be double checked once again
Note: First split attributes by comma, then map to a permanent field (take it out of a list), and then remove the "" from said field
Note: Part 1 / Prep data and remove special characters. Needed first so that the logic downstream works as intended
Note: Examples: / : -----> [nothing/remove] / ~ -----> [nothing/remove] / ) -----> [nothing/remove]
Note: Examples: / 3RD -----> 3RD / FOURTH -----> 4TH
Note: Examples: / IV ----> 4 / VI ----> 6
Note: Part 2 / Standardize numerals. Both for standard and for Roman numerals
Input (input)
    -> Split_by_QCommaQ
Note: Examples: / PHASE TWO A -----> PHASE 2 A / ADDN ONE -----> ADDN 1 / LOT THREE -----> LOT 3
Note: Examples: / PHASE I-A -----> PHASE 1-A / LOT B-II -----> LOT B-3 / PART III-A -----> PART 3-A
Note: Part 3 / Replace keywords and keyphrases with either a standardized equivalent or nothing (remove it). VERY particular about formatting. Use caution when editing these.
Note: Option 1: Replace commonly used keywords or keyphrases with a standardized version. / Examples: / PHASE --> PHS / SECT --> SECTION / CONDO --> CONDOMINIUMS
Output (output)

Bookmark: Prep fields
Split_by_QCommaQ: AttributeSplitter
    ATTR_NAME = text_line_data
    DELIMITER = ,
    DROP_EMPTY_PARTS = No
    LIST_NAME = _ParcelInfo
    TRIM_OPTION = Both
    -> County_Total_Elements
County_Total_Elements: ListElementCounter
    CNT_ATTR = _element_count
    LIST_NAME = _ParcelInfo{}
    -> Filter_Out_Erratic
Note: If the number of elements is not standard (12), continue. Else, send through the uncommon counts section below
Filter_Out_Erratic: Tester
    BOOL_OP = OR
    TEST_CLAUSE = NUM_TEST @Value(_element_count) = 12
    TEST_MODE = NUM_TEST
    PASSED -> element_12
    FAILED -> Uncommon_counts
element_12: AttributeCreator
    ATTR_TABLE:
      SET_TO _SubdName (varchar(200)) = @Value(_ParcelInfo{10})
      SET_TO _ParcelID (varchar(200)) = @Value(_ParcelInfo{0})
    -> Remove_Quotations
Uncommon_counts: TestFilter
    DEFAULT_VALUE = <UNFILTERED>
    PASSED_TEST_GROUP_OUTPUT = FIRST
    TEST_LIST = "BOOL_OP,OR,COMPOSITE_TEST,""""""1"""""",TEST_CLAUSE,TEST @Value(_element_count) = 13",13,"BOOL_OP,OR,COMPOSITE_TEST,""""""1"""""",TEST_CLAUSE,TEST @Value(_element_count) = 14",14,"BOOL_OP,OR,COMPOSITE_TEST,""""""1"""""",TEST_CLAUSE,TEST @Value(_element_count) = 15",15,"BOOL_OP,OR,COMPOSITE_TEST,""""""1"""""",TEST_CLAUSE,TEST @Value(_element_count) = 16",16,"BOOL_OP,OR,COMPOSITE_TEST,""""""1"""""",TEST_CLAUSE,TEST @Value(_element_count) = 17",17,"BOOL_OP,OR,COMPOSITE_TEST,""""""1"""""",TEST_CLAUSE,TEST @Value(_element_count) = 18",18,"BOOL_OP,OR,COMPOSITE_TEST,""""""1"""""",TEST_CLAUSE,TEST @Value(_element_count) = 19",19,"BOOL_OP,OR,COMPOSITE_TEST,""""""1"""""",TEST_CLAUSE,TEST @Value(_element_count) = 20",20,"BOOL_OP,OR,COMPOSITE_TEST,""""""1"""""",TEST_CLAUSE,TEST @Value(_element_count) = 21",21
    13 -> element_13
    14 -> element_14
    15 -> element_15
    16 -> element_16
    17 -> element_17
    18 -> element_18
    19 -> element_19
    20 -> element_20
    21 -> element_21
element_13: AttributeCreator
    ATTR_TABLE:
      SET_TO _SubdName (varchar(200)) = @Value(_ParcelInfo{11})
      SET_TO _ParcelID (varchar(200)) = @Value(_ParcelInfo{0})
    -> Junction
element_18: AttributeCreator
    ATTR_TABLE:
      SET_TO _SubdName (varchar(200)) = @Value(_ParcelInfo{16})
      SET_TO _ParcelID (varchar(200)) = @Value(_ParcelInfo{0})
    -> Junction
element_14: AttributeCreator
    ATTR_TABLE:
      SET_TO _SubdName (varchar(200)) = @Value(_ParcelInfo{12})
      SET_TO _ParcelID (varchar(200)) = @Value(_ParcelInfo{0})
    -> Junction
element_19: AttributeCreator
    ATTR_TABLE:
      SET_TO _SubdName (varchar(200)) = @Value(_ParcelInfo{17})
      SET_TO _ParcelID (varchar(200)) = @Value(_ParcelInfo{0})
    -> Junction
element_15: AttributeCreator
    ATTR_TABLE:
      SET_TO _SubdName (varchar(200)) = @Value(_ParcelInfo{13})
      SET_TO _ParcelID (varchar(200)) = @Value(_ParcelInfo{0})
    -> Junction
element_20: AttributeCreator
    ATTR_TABLE:
      SET_TO _SubdName (varchar(200)) = @Value(_ParcelInfo{18})
      SET_TO _ParcelID (varchar(200)) = @Value(_ParcelInfo{0})
    -> Junction
element_16: AttributeCreator
    ATTR_TABLE:
      SET_TO _SubdName (varchar(200)) = @Value(_ParcelInfo{14})
      SET_TO _ParcelID (varchar(200)) = @Value(_ParcelInfo{0})
    -> Junction
element_21: AttributeCreator
    ATTR_TABLE:
      SET_TO _SubdName (varchar(200)) = @Value(_ParcelInfo{21})
      SET_TO _ParcelID (varchar(200)) = @Value(_ParcelInfo{0})
    -> Junction
element_17: AttributeCreator
    ATTR_TABLE:
      SET_TO _SubdName (varchar(200)) = @Value(_ParcelInfo{15})
      SET_TO _ParcelID (varchar(200)) = @Value(_ParcelInfo{0})
    -> Junction
Junction
    -> Remove_Quotations

Bookmark: Remove Spec Characters
Remove_Quotations: StringReplacer
    CASE = NO
    FIND_TEXT = "
    NO_MATCH = _FME_NO_OP_
    REGEXP = NO
    SRC_ATTRS = _SubdName,_ParcelID
    -> Find_Aposthrophes
Find_Aposthrophes: Tester
    BOOL_OP = OR
    TEST_CLAUSE:
      CASE_INSENSITIVE_TEST @Value(_SubdName) CONTAINS_REGEX '[A-Z]'
      CASE_INSENSITIVE_TEST @Value(_SubdName) CONTAINS_REGEX '[A-Z]+-[0-9]+'
      CASE_INSENSITIVE_TEST @Value(_SubdName) CONTAINS_REGEX '[0-9]+-[A-Z]+'
    TEST_MODE = CASE_INSENSITIVE_TEST
    PASSED -> Remove_Apostrophes
    FAILED -> Hash_or_Number
Remove_Apostrophes: StringReplacer
    CASE = NO
    FIND_TEXT = '
    NO_MATCH = _FME_NO_OP_
    REGEXP = YES
    SRC_ATTRS = _SubdName
    -> Hash_or_Number
Spec_Character_Loop (input)
    -> Hash_or_Number
Hash_or_Number: StringReplacer
    CASE = NO
    FIND_TEXT = #
    NO_MATCH = _FME_NO_OP_
    REGEXP = YES
    SRC_ATTRS = _SubdName
    -> Backtick
Backtick: StringReplacer
    CASE = NO
    FIND_TEXT = `
    NO_MATCH = _FME_NO_OP_
    REGEXP = YES
    SRC_ATTRS = _SubdName
    -> Semicolon
Semicolon: StringReplacer
    CASE = NO
    FIND_TEXT = ;
    NO_MATCH = _FME_NO_OP_
    REGEXP = YES
    SRC_ATTRS = _SubdName
    -> Replace_at_symbol
Replace_at_symbol: StringReplacer
    CASE = NO
    FIND_TEXT = @
    NO_MATCH = _FME_NO_OP_
    REGEXP = NO
    REPLACE_TEXT = " AT "
    SRC_ATTRS = _SubdName
    -> Replace_period
Replace_period: StringReplacer
    CASE = NO
    FIND_TEXT = .
    NO_MATCH = _FME_NO_OP_
    REGEXP = NO
    REPLACE_TEXT = " "
    SRC_ATTRS = _SubdName
    -> Replace_colon
Replace_colon: StringReplacer
    CASE = NO
    FIND_TEXT = :
    NO_MATCH = _FME_NO_OP_
    REGEXP = NO
    REPLACE_TEXT = " "
    SRC_ATTRS = _SubdName
    -> Replace_Tilde
Replace_Tilde: StringReplacer
    CASE = NO
    FIND_TEXT = ~
    NO_MATCH = _FME_NO_OP_
    REGEXP = NO
    REPLACE_TEXT = " "
    SRC_ATTRS = _SubdName
    -> Replace_Parenthesis
Replace_Parenthesis: StringReplacer
    CASE = NO
    FIND_TEXT = (
    NO_MATCH = _FME_NO_OP_
    REGEXP = NO
    REPLACE_TEXT = " "
    SRC_ATTRS = _SubdName
    -> Replace_Parenthesis_2
Replace_Parenthesis_2: StringReplacer
    CASE = NO
    FIND_TEXT = )
    NO_MATCH = _FME_NO_OP_
    REGEXP = NO
    REPLACE_TEXT = " "
    SRC_ATTRS = _SubdName
    -> Re-checK
Re-checK: Tester
    BOOL_OP = OR
    TEST_CLAUSE:
      CASE_INSENSITIVE_TEST @Value(_SubdName) CONTAINS @
      CASE_INSENSITIVE_TEST @Value(_SubdName) CONTAINS .
      CASE_INSENSITIVE_TEST @Value(_SubdName) CONTAINS :
      CASE_INSENSITIVE_TEST @Value(_SubdName) CONTAINS #
      CASE_INSENSITIVE_TEST @Value(_SubdName) CONTAINS `
      CASE_INSENSITIVE_TEST @Value(_SubdName) CONTAINS ;
      CASE_INSENSITIVE_TEST @Value(_SubdName) CONTAINS ~
    TEST_MODE = CASE_INSENSITIVE_TEST
    PASSED -> Spec_Character_Loop (output)
    FAILED -> Numerals

Bookmark: Double Spaces
Spaces (input)
    -> Leading_Trailing_Spaces
Leading_Trailing_Spaces: AttributeTrimmer
    SRC_ATTRS = _SubdName
    TRIM_CHARS = " "
    TRIM_TO_NONE = Yes
    TRIM_TYPE = Both
    -> Junction_7
Junction_7
    -> Numerals

Bookmark: Spec Character Loop
Spec_Character_Loop (output)

Bookmark: Replace Spelled Out Numbers with Numbers (FIRST to 1ST)
Numerals (input)
    -> Numerals
Note: Replace spelled out numerals with numeric versions so it's easier handling later
Numerals: Tester
    BOOL_OP = OR
    TEST_CLAUSE = CASE_INSENSITIVE_TEST @Value(_SubdName) CONTAINS_REGEX ( FIRST | SECOND | THIRD | FOURTH | FIFTH | SIXTH | SEVENTH | EIGHTH | NINTH | TENTH )
    TEST_MODE = CASE_INSENSITIVE_TEST
    PASSED -> FIRST_TO_1ST
    FAILED -> Standard_Numerals
FIRST_TO_1ST: StringReplacer
    CASE = NO
    FIND_TEXT = FIRST
    NO_MATCH = _FME_NO_OP_
    REGEXP = YES
    REPLACE_TEXT = 1ST
    SRC_ATTRS = _SubdName
    -> SECOND_TO_2ND
SECOND_TO_2ND: StringReplacer
    CASE = NO
    FIND_TEXT = SECOND
    NO_MATCH = _FME_NO_OP_
    REGEXP = YES
    REPLACE_TEXT = 2ND
    SRC_ATTRS = _SubdName
    -> THIRD_TO_3RD
THIRD_TO_3RD: StringReplacer
    CASE = NO
    FIND_TEXT = THIRD
    NO_MATCH = _FME_NO_OP_
    REGEXP = YES
    REPLACE_TEXT = 3RD
    SRC_ATTRS = _SubdName
    -> FOURTH_TO_4TH
FOURTH_TO_4TH: StringReplacer
    CASE = NO
    FIND_TEXT = FOURTH
    NO_MATCH = _FME_NO_OP_
    REGEXP = YES
    REPLACE_TEXT = 4TH
    SRC_ATTRS = _SubdName
    -> FIFTH_TO_5TH
FIFTH_TO_5TH: StringReplacer
    CASE = NO
    FIND_TEXT = FIFTH
    NO_MATCH = _FME_NO_OP_
    REGEXP = YES
    REPLACE_TEXT = 5TH
    SRC_ATTRS = _SubdName
    -> SIXTH_TO_6TH
SIXTH_TO_6TH: StringReplacer
    CASE = NO
    FIND_TEXT = SIXTH
    NO_MATCH = _FME_NO_OP_
    REGEXP = YES
    REPLACE_TEXT = 6TH
    SRC_ATTRS = _SubdName
    -> SEVENTH_TO_7TH
SEVENTH_TO_7TH: StringReplacer
    CASE = NO
    FIND_TEXT = SEVENTH
    NO_MATCH = _FME_NO_OP_
    REGEXP = YES
    REPLACE_TEXT = 7TH
    SRC_ATTRS = _SubdName
    -> EIGHTH_TO_8TH
EIGHTH_TO_8TH: StringReplacer
    CASE = NO
    FIND_TEXT = EIGHTH
    NO_MATCH = _FME_NO_OP_
    REGEXP = YES
    REPLACE_TEXT = 8TH
    SRC_ATTRS = _SubdName
    -> NINTH_TO_9TH
NINTH_TO_9TH: StringReplacer
    CASE = NO
    FIND_TEXT = NINTH
    NO_MATCH = _FME_NO_OP_
    REGEXP = YES
    REPLACE_TEXT = 9TH
    SRC_ATTRS = _SubdName
    -> TENTH_TO_10TH
TENTH_TO_10TH: StringReplacer
    CASE = NO
    FIND_TEXT = TENTH
    NO_MATCH = _FME_NO_OP_
    REGEXP = YES
    REPLACE_TEXT = 10TH
    SRC_ATTRS = _SubdName
    -> Send_Back_Nm
Send_Back_Nm: Tester
    BOOL_OP = OR
    TEST_CLAUSE = CASE_INSENSITIVE_TEST @Value(_SubdName) CONTAINS_REGEX ( FIRST | SECOND | THIRD | FOURTH | FIFTH | SIXTH | SEVENTH | EIGHTH | NINTH | TENTH )
    TEST_MODE = CASE_INSENSITIVE_TEST
    PASSED -> Numerals (output)
    FAILED -> Standard_Numerals

Bookmark: Numerals Loop
Numerals (output)

Bookmark: Standardize roman numerals that are between spaces. Example: the "II" in Phase II A"
Roman_Numerals (input)
    -> Roman_Numerals
Note: Note: only changes instances with roman numerals at the beginning middle (with spaces on both sides) or end of a string
Roman_Numerals: Tester
    BOOL_OP = OR
    TEST_CLAUSE = CASE_SENSITIVE_TEST @Value(_SubdName) CONTAINS_REGEX (^I | I | I$|^II | II | II$|^III | III | III$|^IV | IV | IV$|^V | V | V$|^VI | VI | VI$|^VII | VII | VII$|^VIII | VIII | VIII$|^IX | IX | IX$|^X | X | X$)
    TEST_MODE = CASE_SENSITIVE_TEST
    PASSED -> _I_
    FAILED -> Rom_Num_Dash
_I_: StringReplacer
    CASE = NO
    FIND_TEXT = (^I | I | I$)
    NO_MATCH = _FME_NO_OP_
    REGEXP = YES
    REPLACE_TEXT = " 1 "
    SRC_ATTRS = _SubdName
    -> _II_
_II_: StringReplacer
    CASE = NO
    FIND_TEXT = (^II | II | II$)
    NO_MATCH = _FME_NO_OP_
    REGEXP = YES
    REPLACE_TEXT = " 2 "
    SRC_ATTRS = _SubdName
    -> _III_
_III_: StringReplacer
    CASE = NO
    FIND_TEXT = (^III | III | III$)
    NO_MATCH = _FME_NO_OP_
    REGEXP = YES
    REPLACE_TEXT = " 3 "
    SRC_ATTRS = _SubdName
    -> _IV_
_IV_: StringReplacer
    CASE = NO
    FIND_TEXT = (^IV | IV | IV$)
    NO_MATCH = _FME_NO_OP_
    REGEXP = YES
    REPLACE_TEXT = " 4 "
    SRC_ATTRS = _SubdName
    -> _V_
_V_: StringReplacer
    CASE = NO
    FIND_TEXT = (^V | V | V$)
    NO_MATCH = _FME_NO_OP_
    REGEXP = YES
    REPLACE_TEXT = " 5 "
    SRC_ATTRS = _SubdName
    -> _VI_
_VI_: StringReplacer
    CASE = NO
    FIND_TEXT = (^VI | VI | VI$)
    NO_MATCH = _FME_NO_OP_
    REGEXP = YES
    REPLACE_TEXT = " 6 "
    SRC_ATTRS = _SubdName
    -> _VII_
_VII_: StringReplacer
    CASE = NO
    FIND_TEXT = (^VII | VII | VII$)
    NO_MATCH = _FME_NO_OP_
    REGEXP = YES
    REPLACE_TEXT = " 7 "
    SRC_ATTRS = _SubdName
    -> _VIII_
_VIII_: StringReplacer
    CASE = NO
    FIND_TEXT = (^VIII | VIII | VIII$)
    NO_MATCH = _FME_NO_OP_
    REGEXP = YES
    REPLACE_TEXT = " 8 "
    SRC_ATTRS = _SubdName
    -> _IX_
_IX_: StringReplacer
    CASE = NO
    FIND_TEXT = (^IX | IX | IX$)
    NO_MATCH = _FME_NO_OP_
    REGEXP = YES
    REPLACE_TEXT = " 9 "
    SRC_ATTRS = _SubdName
    -> _X_
_X_: StringReplacer
    CASE = NO
    FIND_TEXT = (^X | X | X$)
    NO_MATCH = _FME_NO_OP_
    REGEXP = YES
    REPLACE_TEXT = " 10 "
    SRC_ATTRS = _SubdName
    -> Roman_Numerals_2
Roman_Numerals_2: Tester
    BOOL_OP = OR
    TEST_CLAUSE = CASE_INSENSITIVE_TEST @Value(_SubdName) CONTAINS_REGEX (^I | I | I$|^II | II | II$|^III | III | III$|^IV | IV | IV$|^V | V | V$|^VI | VI | VI$|^VII | VII | VII$|^VIII | VIII | VIII$|^IX | IX | IX$|^X | X | X$)
    TEST_MODE = CASE_INSENSITIVE_TEST
    PASSED -> Roman_Numerals (output)
    FAILED -> Rom_Num_Dash

Bookmark: Convert standard spelled out numerals to numbers
Numeral_Pt_2 (input)
    -> Standard_Numerals
Note: For I-1, an exemption is made to make sure that legitimate names like I-40 are not changed. Also added an exception for examples like X-L (extra large)
Standard_Numerals: TestFilter
    DEFAULT_VALUE = <Unfiltered>
    PASSED_TEST_GROUP_OUTPUT = FIRST
    TEST_LIST = "BOOL_OP,OR,COMPOSITE_TEST,""""""1"""""",TEST_CLAUSE,CASE_INSENSITIVE_TEST @Value(_SubdName) CONTAINS_REGEX ( ONE | ONE$)",1,"BOOL_OP,OR,COMPOSITE_TEST,""""""1"""""",TEST_CLAUSE,CASE_INSENSITIVE_TEST @Value(_SubdName) CONTAINS_REGEX ( TWO | TWO$)",2,"BOOL_OP,OR,COMPOSITE_TEST,""""""1"""""",TEST_CLAUSE,CASE_INSENSITIVE_TEST @Value(_SubdName) CONTAINS_REGEX ( THREE | THREE$)",3,"BOOL_OP,OR,COMPOSITE_TEST,""""""1"""""",TEST_CLAUSE,CASE_INSENSITIVE_TEST @Value(_SubdName) CONTAINS_REGEX ( FOUR | FOUR$)",4,"BOOL_OP,OR,COMPOSITE_TEST,""""""1"""""",TEST_CLAUSE,CASE_INSENSITIVE_TEST @Value(_SubdName) CONTAINS_REGEX ( FIVE | FIVE$)",5,"BOOL_OP,OR,COMPOSITE_TEST,""""""1"""""",TEST_CLAUSE,CASE_INSENSITIVE_TEST @Value(_SubdName) CONTAINS_REGEX ( SIX | SIX$)",6,"BOOL_OP,OR,COMPOSITE_TEST,""""""1"""""",TEST_CLAUSE,CASE_INSENSITIVE_TEST @Value(_SubdName) CONTAINS_REGEX ( SEVEN | SEVEN$)",7,"BOOL_OP,OR,COMPOSITE_TEST,""""""1"""""",TEST_CLAUSE,CASE_INSENSITIVE_TEST @Value(_SubdName) CONTAINS_REGEX ( EIGHT | EIGHT$)",8,"BOOL_OP,OR,COMPOSITE_TEST,""""""1"""""",TEST_CLAUSE,CASE_INSENSITIVE_TEST @Value(_SubdName) CONTAINS_REGEX ( NINE | NINE$)",9,"BOOL_OP,OR,COMPOSITE_TEST,""""""1"""""",TEST_CLAUSE,CASE_INSENSITIVE_TEST @Value(_SubdName) CONTAINS_REGEX ( TEN | TEN$)",10
    1 -> _ONE_
    2 -> _TWO_
    3 -> _THREE_
    4 -> _FOUR_
    5 -> _FIVE_
    6 -> _SIX_
    7 -> _SEVEN_
    8 -> _EIGHT_
    9 -> _NINE_
    10 -> _TEN_
    <Unfiltered> -> Roman_Numerals
_ONE_: StringReplacer
    CASE = NO
    FIND_TEXT = " ONE "
    NO_MATCH = _FME_NO_OP_
    REGEXP = YES
    REPLACE_TEXT = " 1 "
    SRC_ATTRS = _SubdName
    -> _ONE
Note: Given how highly unlikely it would be for a spelled out numeral to begin a string, those are not being accounted for. To be clear, they *can* exist there legitimately, but if that's the case, they are very likely part of the official name
_ONE: StringReplacer
    CASE = NO
    FIND_TEXT = " ONE"
    NO_MATCH = _FME_NO_OP_
    REGEXP = YES
    REPLACE_TEXT = " 1"
    SRC_ATTRS = _SubdName
    -> Send_Back_SN
_TWO_: StringReplacer
    CASE = NO
    FIND_TEXT = " TWO "
    NO_MATCH = _FME_NO_OP_
    REGEXP = YES
    REPLACE_TEXT = " 2 "
    SRC_ATTRS = _SubdName
    -> _TWO
_TWO: StringReplacer
    CASE = NO
    FIND_TEXT = " TWO"
    NO_MATCH = _FME_NO_OP_
    REGEXP = YES
    REPLACE_TEXT = " 2"
    SRC_ATTRS = _SubdName
    -> Send_Back_SN
_THREE_: StringReplacer
    CASE = NO
    FIND_TEXT = " THREE "
    NO_MATCH = _FME_NO_OP_
    REGEXP = YES
    REPLACE_TEXT = " 3 "
    SRC_ATTRS = _SubdName
    -> _THREE
_THREE: StringReplacer
    CASE = NO
    FIND_TEXT = " THREE"
    NO_MATCH = _FME_NO_OP_
    REGEXP = YES
    REPLACE_TEXT = " 3"
    SRC_ATTRS = _SubdName
    -> Send_Back_SN
_FOUR_: StringReplacer
    CASE = NO
    FIND_TEXT = " FOUR "
    NO_MATCH = _FME_NO_OP_
    REGEXP = YES
    REPLACE_TEXT = " 4 "
    SRC_ATTRS = _SubdName
    -> _FOUR
_FOUR: StringReplacer
    CASE = NO
    FIND_TEXT = " FOUR"
    NO_MATCH = _FME_NO_OP_
    REGEXP = YES
    REPLACE_TEXT = " 4"
    SRC_ATTRS = _SubdName
    -> Send_Back_SN
_FIVE_: StringReplacer
    CASE = NO
    FIND_TEXT = " FIVE "
    NO_MATCH = _FME_NO_OP_
    REGEXP = YES
    REPLACE_TEXT = " 5 "
    SRC_ATTRS = _SubdName
    -> _FIVE
_FIVE: StringReplacer
    CASE = NO
    FIND_TEXT = " FIVE"
    NO_MATCH = _FME_NO_OP_
    REGEXP = YES
    REPLACE_TEXT = " 5"
    SRC_ATTRS = _SubdName
    -> Send_Back_SN
_SIX_: StringReplacer
    CASE = NO
    FIND_TEXT = " SIX "
    NO_MATCH = _FME_NO_OP_
    REGEXP = YES
    REPLACE_TEXT = " 6 "
    SRC_ATTRS = _SubdName
    -> _SIX
_SIX: StringReplacer
    CASE = NO
    FIND_TEXT = " SIX"
    NO_MATCH = _FME_NO_OP_
    REGEXP = YES
    REPLACE_TEXT = " 6"
    SRC_ATTRS = _SubdName
    -> Send_Back_SN
_SEVEN_: StringReplacer
    CASE = NO
    FIND_TEXT = " SEVEN "
    NO_MATCH = _FME_NO_OP_
    REGEXP = YES
    REPLACE_TEXT = " 7 "
    SRC_ATTRS = _SubdName
    -> _SEVEN
_SEVEN: StringReplacer
    CASE = NO
    FIND_TEXT = " SEVEN"
    NO_MATCH = _FME_NO_OP_
    REGEXP = YES
    REPLACE_TEXT = " 7"
    SRC_ATTRS = _SubdName
    -> Send_Back_SN
_EIGHT_: StringReplacer
    CASE = NO
    FIND_TEXT = " EIGHT "
    NO_MATCH = _FME_NO_OP_
    REGEXP = YES
    REPLACE_TEXT = " 8 "
    SRC_ATTRS = _SubdName
    -> _EIGHT
_EIGHT: StringReplacer
    CASE = NO
    FIND_TEXT = " EIGHT"
    NO_MATCH = _FME_NO_OP_
    REGEXP = YES
    REPLACE_TEXT = " 8"
    SRC_ATTRS = _SubdName
    -> Send_Back_SN
_NINE_: StringReplacer
    CASE = NO
    FIND_TEXT = " NINE "
    NO_MATCH = _FME_NO_OP_
    REGEXP = YES
    REPLACE_TEXT = " 9 "
    SRC_ATTRS = _SubdName
    -> _NINE
_NINE: StringReplacer
    CASE = NO
    FIND_TEXT = " NINE"
    NO_MATCH = _FME_NO_OP_
    REGEXP = YES
    REPLACE_TEXT = " 9"
    SRC_ATTRS = _SubdName
    -> Send_Back_SN
_TEN_: StringReplacer
    CASE = NO
    FIND_TEXT = " TEN "
    NO_MATCH = _FME_NO_OP_
    REGEXP = YES
    REPLACE_TEXT = " 10 "
    SRC_ATTRS = _SubdName
    -> _TEN
_TEN: StringReplacer
    CASE = NO
    FIND_TEXT = " TEN"
    NO_MATCH = _FME_NO_OP_
    REGEXP = YES
    REPLACE_TEXT = " 10"
    SRC_ATTRS = _SubdName
    -> Send_Back_SN
Send_Back_SN: TestFilter
    DEFAULT_VALUE = <Unfiltered>
    PASSED_TEST_GROUP_OUTPUT = FIRST
    TEST_LIST = "BOOL_OP,OR,COMPOSITE_TEST,""""""1"""""",TEST_CLAUSE,CASE_INSENSITIVE_TEST @Value(_SubdName) CONTAINS_REGEX ( ONE | ONE$)",Send Back,"BOOL_OP,OR,COMPOSITE_TEST,""""""1"""""",TEST_CLAUSE,CASE_INSENSITIVE_TEST @Value(_SubdName) CONTAINS_REGEX ( TWO | TWO$)",Send Back,"BOOL_OP,OR,COMPOSITE_TEST,""""""1"""""",TEST_CLAUSE,CASE_INSENSITIVE_TEST @Value(_SubdName) CONTAINS_REGEX ( THREE | THREE$)",Send Back,"BOOL_OP,OR,COMPOSITE_TEST,""""""1"""""",TEST_CLAUSE,CASE_INSENSITIVE_TEST @Value(_SubdName) CONTAINS_REGEX ( FOUR | FOUR$)",Send Back,"BOOL_OP,OR,COMPOSITE_TEST,""""""1"""""",TEST_CLAUSE,CASE_INSENSITIVE_TEST @Value(_SubdName) CONTAINS_REGEX ( FIVE | FIVE$)",Send Back,"BOOL_OP,OR,COMPOSITE_TEST,""""""1"""""",TEST_CLAUSE,CASE_INSENSITIVE_TEST @Value(_SubdName) CONTAINS_REGEX ( SIX | SIX$)",Send Back,"BOOL_OP,OR,COMPOSITE_TEST,""""""1"""""",TEST_CLAUSE,CASE_INSENSITIVE_TEST @Value(_SubdName) CONTAINS_REGEX ( SEVEN | SEVEN$)",Send Back,"BOOL_OP,OR,COMPOSITE_TEST,""""""1"""""",TEST_CLAUSE,CASE_INSENSITIVE_TEST @Value(_SubdName) CONTAINS_REGEX ( EIGHT | EIGHT$)",Send Back,"BOOL_OP,OR,COMPOSITE_TEST,""""""1"""""",TEST_CLAUSE,CASE_INSENSITIVE_TEST @Value(_SubdName) CONTAINS_REGEX ( NINE | NINE$)",Send Back,"BOOL_OP,OR,COMPOSITE_TEST,""""""1"""""",TEST_CLAUSE,CASE_INSENSITIVE_TEST @Value(_SubdName) CONTAINS_REGEX ( TEN | TEN$)",Send Back
    Send Back -> Numeral_Pt_2 (output)
    <Unfiltered> -> Roman_Numerals

Bookmark: Numerals Pt 2 Loop
Numeral_Pt_2 (output)

Bookmark: Roman Numerals Loop
Roman_Numerals (output)

Bookmark: Standardize roman numerals that are either preceded or followed by a dash. Example II-A
Rom_Num_Dash (input)
    -> Rom_Num_Dash
Note: For I-1, an exemption is made to make sure that legitimate names like I-40 are not changed. Also added an exception for examples like X-L (extra large)
Rom_Num_Dash: TestFilter
    DEFAULT_VALUE = <UNFILTERED>
    PASSED_TEST_GROUP_OUTPUT = FIRST
    TEST_LIST:
      "BOOL_OP,OR,COMPOSITE_TEST,""""""1 OR 2 OR 3 OR 4 OR 5"""""",TEST_CLAUSE,CASE_INSENSITIVE_TEST @Value(_SubdName) CONTAINS_REGEX  I-[0-9]+
      CASE_INSENSITIVE_TEST @Value(_SubdName) CONTAINS_REGEX  [0-9]+-I
      CASE_INSENSITIVE_TEST @Value(_SubdName) CONTAINS_REGEX  I-[A-Z]+
      CASE_INSENSITIVE_TEST @Value(_SubdName) CONTAINS_REGEX  [A-Z]+-I
      CASE_INSENSITIVE_TEST @Value(_SubdName) CONTAINS_REGEX  I$",-I-,"BOOL_OP,OR,COMPOSITE_TEST,""""""1 OR 2 OR 3 OR 4 OR 5"""""",TEST_CLAUSE,CASE_INSENSITIVE_TEST @Value(_SubdName) CONTAINS_REGEX  II-[0-9]+
      CASE_INSENSITIVE_TEST @Value(_SubdName) CONTAINS_REGEX  [0-9]+-II
      CASE_INSENSITIVE_TEST @Value(_SubdName) CONTAINS_REGEX  II-[A-Z]+
      CASE_INSENSITIVE_TEST @Value(_SubdName) CONTAINS_REGEX  [A-Z]+-II
      CASE_INSENSITIVE_TEST @Value(_SubdName) CONTAINS_REGEX  II$",-II-,"BOOL_OP,OR,COMPOSITE_TEST,""""""1 OR 2 OR 3 OR 4 OR 5"""""",TEST_CLAUSE,CASE_INSENSITIVE_TEST @Value(_SubdName) CONTAINS_REGEX  III-[0-9]+
      CASE_INSENSITIVE_TEST @Value(_SubdName) CONTAINS_REGEX  [0-9]+-III
      CASE_INSENSITIVE_TEST @Value(_SubdName) CONTAINS_REGEX  III-[A-Z]+
      CASE_INSENSITIVE_TEST @Value(_SubdName) CONTAINS_REGEX  [A-Z]+-III
      CASE_INSENSITIVE_TEST @Value(_SubdName) CONTAINS_REGEX  III$",-III-,"BOOL_OP,OR,COMPOSITE_TEST,""""""1 OR 2 OR 3 OR 4 OR 5"""""",TEST_CLAUSE,CASE_INSENSITIVE_TEST @Value(_SubdName) CONTAINS_REGEX  IV-[0-9]+
      CASE_INSENSITIVE_TEST @Value(_SubdName) CONTAINS_REGEX  [0-9]+-IV
      CASE_INSENSITIVE_TEST @Value(_SubdName) CONTAINS_REGEX  IV-[A-Z]+
      CASE_INSENSITIVE_TEST @Value(_SubdName) CONTAINS_REGEX  [A-Z]+-IV
      CASE_INSENSITIVE_TEST @Value(_SubdName) CONTAINS_REGEX  IV$",-IV-,"BOOL_OP,OR,COMPOSITE_TEST,""""""1 OR 2 OR 3 OR 4 OR 5"""""",TEST_CLAUSE,CASE_INSENSITIVE_TEST @Value(_SubdName) CONTAINS_REGEX  V-[0-9]+
      CASE_INSENSITIVE_TEST @Value(_SubdName) CONTAINS_REGEX  [0-9]+-V
      CASE_INSENSITIVE_TEST @Value(_SubdName) CONTAINS_REGEX  V-[A-Z]+
      CASE_INSENSITIVE_TEST @Value(_SubdName) CONTAINS_REGEX  [A-Z]+-V
      CASE_INSENSITIVE_TEST @Value(_SubdName) CONTAINS_REGEX  V$",-V-,"BOOL_OP,OR,COMPOSITE_TEST,""""""1 OR 2 OR 3 OR 4 OR 5"""""",TEST_CLAUSE,CASE_INSENSITIVE_TEST @Value(_SubdName) CONTAINS_REGEX  VI-[0-9]+
      CASE_INSENSITIVE_TEST @Value(_SubdName) CONTAINS_REGEX  [0-9]+-VI
      CASE_INSENSITIVE_TEST @Value(_SubdName) CONTAINS_REGEX  VI-[A-Z]+
      CASE_INSENSITIVE_TEST @Value(_SubdName) CONTAINS_REGEX  [A-Z]+-VI
      CASE_INSENSITIVE_TEST @Value(_SubdName) CONTAINS_REGEX  VI$",-VI-,"BOOL_OP,OR,COMPOSITE_TEST,""""""1 OR 2 OR 3 OR 4 OR 5"""""",TEST_CLAUSE,CASE_INSENSITIVE_TEST @Value(_SubdName) CONTAINS_REGEX  VII-[0-9]+
      CASE_INSENSITIVE_TEST @Value(_SubdName) CONTAINS_REGEX  [0-9]+-VII
      CASE_INSENSITIVE_TEST @Value(_SubdName) CONTAINS_REGEX  VII-[A-Z]+
      CASE_INSENSITIVE_TEST @Value(_SubdName) CONTAINS_REGEX  [A-Z]+-VII
      CASE_INSENSITIVE_TEST @Value(_SubdName) CONTAINS_REGEX  VII$",-VII-,"BOOL_OP,OR,COMPOSITE_TEST,""""""1 OR 2 OR 3 OR 4 OR 5"""""",TEST_CLAUSE,CASE_INSENSITIVE_TEST @Value(_SubdName) CONTAINS_REGEX  VIII-[0-9]+
      CASE_INSENSITIVE_TEST @Value(_SubdName) CONTAINS_REGEX  [0-9]+-VIII
      CASE_INSENSITIVE_TEST @Value(_SubdName) CONTAINS_REGEX  VIII-[A-Z]+
      CASE_INSENSITIVE_TEST @Value(_SubdName) CONTAINS_REGEX  [A-Z]+-VIII
      CASE_INSENSITIVE_TEST @Value(_SubdName) CONTAINS_REGEX  VIII$",-VIII-,"BOOL_OP,OR,COMPOSITE_TEST,""""""1 OR 2 OR 3 OR 4 OR 5"""""",TEST_CLAUSE,CASE_INSENSITIVE_TEST @Value(_SubdName) CONTAINS_REGEX  IX-[0-9]+
      CASE_INSENSITIVE_TEST @Value(_SubdName) CONTAINS_REGEX  [0-9]+-IX
      CASE_INSENSITIVE_TEST @Value(_SubdName) CONTAINS_REGEX  IX-[A-Z]+
      CASE_INSENSITIVE_TEST @Value(_SubdName) CONTAINS_REGEX  [A-Z]+-IX
      CASE_INSENSITIVE_TEST @Value(_SubdName) CONTAINS_REGEX  IX$",-IX-,"BOOL_OP,OR,COMPOSITE_TEST,""""""1 OR 2 OR 3 OR 4 OR 5"""""",TEST_CLAUSE,CASE_INSENSITIVE_TEST @Value(_SubdName) CONTAINS_REGEX  X-[0-9]+
      CASE_INSENSITIVE_TEST @Value(_SubdName) CONTAINS_REGEX  [0-9]+-X
      CASE_INSENSITIVE_TEST @Value(_SubdName) CONTAINS_REGEX  X-[A-Z]+
      CASE_INSENSITIVE_TEST @Value(_SubdName) CONTAINS_REGEX  [A-Z]+-X
      CASE_INSENSITIVE_TEST @Value(_SubdName) CONTAINS_REGEX  X$",-X-
    -I- -> I-
    -II- -> II-
    -III- -> III-
    -IV- -> IV-
    -V- -> V-
    -VI- -> VI-
    -VII- -> VII-
    -VIII- -> VIII-
    -IX- -> IX-
    -X- -> X-
    <UNFILTERED> -> Standard_Keyphrases
I-: StringReplacer
    CASE = NO
    FIND_TEXT = I-
    NO_MATCH = _FME_NO_OP_
    REGEXP = YES
    REPLACE_TEXT = 1-
    SRC_ATTRS = _SubdName
    -> -I
-I: StringReplacer
    CASE = NO
    FIND_TEXT = -I
    NO_MATCH = _FME_NO_OP_
    REGEXP = YES
    REPLACE_TEXT = -1
    SRC_ATTRS = _SubdName
    -> Rom_Num_Dash_3
II-: StringReplacer
    CASE = NO
    FIND_TEXT = II-
    NO_MATCH = _FME_NO_OP_
    REGEXP = YES
    REPLACE_TEXT = 2-
    SRC_ATTRS = _SubdName
    -> -II
-II: StringReplacer
    CASE = NO
    FIND_TEXT = -II
    NO_MATCH = _FME_NO_OP_
    REGEXP = YES
    REPLACE_TEXT = -2
    SRC_ATTRS = _SubdName
    -> Rom_Num_Dash_3
III-: StringReplacer
    CASE = NO
    FIND_TEXT = III-
    NO_MATCH = _FME_NO_OP_
    REGEXP = YES
    REPLACE_TEXT = 3-
    SRC_ATTRS = _SubdName
    -> -III
-III: StringReplacer
    CASE = NO
    FIND_TEXT = -III
    NO_MATCH = _FME_NO_OP_
    REGEXP = YES
    REPLACE_TEXT = -3
    SRC_ATTRS = _SubdName
    -> Rom_Num_Dash_3
IV-: StringReplacer
    CASE = NO
    FIND_TEXT = IV-
    NO_MATCH = _FME_NO_OP_
    REGEXP = YES
    REPLACE_TEXT = 4-
    SRC_ATTRS = _SubdName
    -> -IV
-IV: StringReplacer
    CASE = NO
    FIND_TEXT = -IV
    NO_MATCH = _FME_NO_OP_
    REGEXP = YES
    REPLACE_TEXT = -4
    SRC_ATTRS = _SubdName
    -> Rom_Num_Dash_3
V-: StringReplacer
    CASE = NO
    FIND_TEXT = V-
    NO_MATCH = _FME_NO_OP_
    REGEXP = YES
    REPLACE_TEXT = 5-
    SRC_ATTRS = _SubdName
    -> -V
-V: StringReplacer
    CASE = NO
    FIND_TEXT = -V
    NO_MATCH = _FME_NO_OP_
    REGEXP = YES
    REPLACE_TEXT = -5
    SRC_ATTRS = _SubdName
    -> Rom_Num_Dash_3
VI-: StringReplacer
    CASE = NO
    FIND_TEXT = VI-
    NO_MATCH = _FME_NO_OP_
    REGEXP = YES
    REPLACE_TEXT = 6-
    SRC_ATTRS = _SubdName
    -> -VI
-VI: StringReplacer
    CASE = NO
    FIND_TEXT = -VI
    NO_MATCH = _FME_NO_OP_
    REGEXP = YES
    REPLACE_TEXT = -6
    SRC_ATTRS = _SubdName
    -> Rom_Num_Dash_3
VII-: StringReplacer
    CASE = NO
    FIND_TEXT = VII-
    NO_MATCH = _FME_NO_OP_
    REGEXP = YES
    REPLACE_TEXT = 7-
    SRC_ATTRS = _SubdName
    -> -VII
-VII: StringReplacer
    CASE = NO
    FIND_TEXT = -VII
    NO_MATCH = _FME_NO_OP_
    REGEXP = YES
    REPLACE_TEXT = -7
    SRC_ATTRS = _SubdName
    -> Rom_Num_Dash_3
VIII-: StringReplacer
    CASE = NO
    FIND_TEXT = VIII-
    NO_MATCH = _FME_NO_OP_
    REGEXP = YES
    REPLACE_TEXT = 8-
    SRC_ATTRS = _SubdName
    -> -VIII
-VIII: StringReplacer
    CASE = NO
    FIND_TEXT = -VIII
    NO_MATCH = _FME_NO_OP_
    REGEXP = YES
    REPLACE_TEXT = -8
    SRC_ATTRS = _SubdName
    -> Rom_Num_Dash_3
IX-: StringReplacer
    CASE = NO
    FIND_TEXT = IX-
    NO_MATCH = _FME_NO_OP_
    REGEXP = YES
    REPLACE_TEXT = 9-
    SRC_ATTRS = _SubdName
    -> -IX
-IX: StringReplacer
    CASE = NO
    FIND_TEXT = -IX
    NO_MATCH = _FME_NO_OP_
    REGEXP = YES
    REPLACE_TEXT = -9
    SRC_ATTRS = _SubdName
    -> Rom_Num_Dash_3
X-: StringReplacer
    CASE = NO
    FIND_TEXT = X-
    NO_MATCH = _FME_NO_OP_
    REGEXP = YES
    REPLACE_TEXT = 10-
    SRC_ATTRS = _SubdName
    -> -X
-X: StringReplacer
    CASE = NO
    FIND_TEXT = -X
    NO_MATCH = _FME_NO_OP_
    REGEXP = YES
    REPLACE_TEXT = -10
    SRC_ATTRS = _SubdName
    -> Rom_Num_Dash_3
Rom_Num_Dash_3: TestFilter
    DEFAULT_VALUE = <UNFILTERED>
    PASSED_TEST_GROUP_OUTPUT = FIRST
    TEST_LIST:
      "BOOL_OP,OR,COMPOSITE_TEST,""""""1 OR 2 OR 3 OR 4 OR 5"""""",TEST_CLAUSE,CASE_INSENSITIVE_TEST @Value(_SubdName) CONTAINS_REGEX  I-[0-9]+
      CASE_INSENSITIVE_TEST @Value(_SubdName) CONTAINS_REGEX  [0-9]+-I
      CASE_INSENSITIVE_TEST @Value(_SubdName) CONTAINS_REGEX  I-[A-Z]+
      CASE_INSENSITIVE_TEST @Value(_SubdName) CONTAINS_REGEX  [A-Z]+-I
      CASE_INSENSITIVE_TEST @Value(_SubdName) CONTAINS_REGEX  I$",Send Back,"BOOL_OP,OR,COMPOSITE_TEST,""""""1 OR 2 OR 3 OR 4 OR 5"""""",TEST_CLAUSE,CASE_INSENSITIVE_TEST @Value(_SubdName) CONTAINS_REGEX  II-[0-9]+
      CASE_INSENSITIVE_TEST @Value(_SubdName) CONTAINS_REGEX  [0-9]+-II
      CASE_INSENSITIVE_TEST @Value(_SubdName) CONTAINS_REGEX  II-[A-Z]+
      CASE_INSENSITIVE_TEST @Value(_SubdName) CONTAINS_REGEX  [A-Z]+-II
      CASE_INSENSITIVE_TEST @Value(_SubdName) CONTAINS_REGEX  II$",Send Back,"BOOL_OP,OR,COMPOSITE_TEST,""""""1 OR 2 OR 3 OR 4 OR 5"""""",TEST_CLAUSE,CASE_INSENSITIVE_TEST @Value(_SubdName) CONTAINS_REGEX  III-[0-9]+
      CASE_INSENSITIVE_TEST @Value(_SubdName) CONTAINS_REGEX  [0-9]+-III
      CASE_INSENSITIVE_TEST @Value(_SubdName) CONTAINS_REGEX  III-[A-Z]+
      CASE_INSENSITIVE_TEST @Value(_SubdName) CONTAINS_REGEX  [A-Z]+-III
      CASE_INSENSITIVE_TEST @Value(_SubdName) CONTAINS_REGEX  III$",Send Back,"BOOL_OP,OR,COMPOSITE_TEST,""""""1 OR 2 OR 3 OR 4 OR 5"""""",TEST_CLAUSE,CASE_INSENSITIVE_TEST @Value(_SubdName) CONTAINS_REGEX  IV-[0-9]+
      CASE_INSENSITIVE_TEST @Value(_SubdName) CONTAINS_REGEX  [0-9]+-IV
      CASE_INSENSITIVE_TEST @Value(_SubdName) CONTAINS_REGEX  IV-[A-Z]+
      CASE_INSENSITIVE_TEST @Value(_SubdName) CONTAINS_REGEX  [A-Z]+-IV
      CASE_INSENSITIVE_TEST @Value(_SubdName) CONTAINS_REGEX  IV$",Send Back,"BOOL_OP,OR,COMPOSITE_TEST,""""""1 OR 2 OR 3 OR 4 OR 5"""""",TEST_CLAUSE,CASE_INSENSITIVE_TEST @Value(_SubdName) CONTAINS_REGEX  V-[0-9]+
      CASE_INSENSITIVE_TEST @Value(_SubdName) CONTAINS_REGEX  [0-9]+-V
      CASE_INSENSITIVE_TEST @Value(_SubdName) CONTAINS_REGEX  V-[A-Z]+
      CASE_INSENSITIVE_TEST @Value(_SubdName) CONTAINS_REGEX  [A-Z]+-V
      CASE_INSENSITIVE_TEST @Value(_SubdName) CONTAINS_REGEX  V$",Send Back,"BOOL_OP,OR,COMPOSITE_TEST,""""""1 OR 2 OR 3 OR 4 OR 5"""""",TEST_CLAUSE,CASE_INSENSITIVE_TEST @Value(_SubdName) CONTAINS_REGEX  VI-[0-9]+
      CASE_INSENSITIVE_TEST @Value(_SubdName) CONTAINS_REGEX  [0-9]+-VI
      CASE_INSENSITIVE_TEST @Value(_SubdName) CONTAINS_REGEX  VI-[A-Z]+
      CASE_INSENSITIVE_TEST @Value(_SubdName) CONTAINS_REGEX  [A-Z]+-VI
      CASE_INSENSITIVE_TEST @Value(_SubdName) CONTAINS_REGEX  VI$",Send Back,"BOOL_OP,OR,COMPOSITE_TEST,""""""1 OR 2 OR 3 OR 4 OR 5"""""",TEST_CLAUSE,CASE_INSENSITIVE_TEST @Value(_SubdName) CONTAINS_REGEX  VII-[0-9]+
      CASE_INSENSITIVE_TEST @Value(_SubdName) CONTAINS_REGEX  [0-9]+-VII
      CASE_INSENSITIVE_TEST @Value(_SubdName) CONTAINS_REGEX  VII-[A-Z]+
      CASE_INSENSITIVE_TEST @Value(_SubdName) CONTAINS_REGEX  [A-Z]+-VII
      CASE_INSENSITIVE_TEST @Value(_SubdName) CONTAINS_REGEX  VII$",Send Back,"BOOL_OP,OR,COMPOSITE_TEST,""""""1 OR 2 OR 3 OR 4 OR 5"""""",TEST_CLAUSE,CASE_INSENSITIVE_TEST @Value(_SubdName) CONTAINS_REGEX  VIII-[0-9]+
      CASE_INSENSITIVE_TEST @Value(_SubdName) CONTAINS_REGEX  [0-9]+-VIII
      CASE_INSENSITIVE_TEST @Value(_SubdName) CONTAINS_REGEX  VIII-[A-Z]+
      CASE_INSENSITIVE_TEST @Value(_SubdName) CONTAINS_REGEX  [A-Z]+-VIII
      CASE_INSENSITIVE_TEST @Value(_SubdName) CONTAINS_REGEX  VIII$",Send Back,"BOOL_OP,OR,COMPOSITE_TEST,""""""1 OR 2 OR 3 OR 4 OR 5"""""",TEST_CLAUSE,CASE_INSENSITIVE_TEST @Value(_SubdName) CONTAINS_REGEX  IX-[0-9]+
      CASE_INSENSITIVE_TEST @Value(_SubdName) CONTAINS_REGEX  [0-9]+-IX
      CASE_INSENSITIVE_TEST @Value(_SubdName) CONTAINS_REGEX  IX-[A-Z]+
      CASE_INSENSITIVE_TEST @Value(_SubdName) CONTAINS_REGEX  [A-Z]+-IX
      CASE_INSENSITIVE_TEST @Value(_SubdName) CONTAINS_REGEX  IX$",Send Back,"BOOL_OP,OR,COMPOSITE_TEST,""""""1 OR 2 OR 3 OR 4 OR 5"""""",TEST_CLAUSE,CASE_INSENSITIVE_TEST @Value(_SubdName) CONTAINS_REGEX  X-[0-9]+
      CASE_INSENSITIVE_TEST @Value(_SubdName) CONTAINS_REGEX  [0-9]+-X
      CASE_INSENSITIVE_TEST @Value(_SubdName) CONTAINS_REGEX  X-[A-Z]+
      CASE_INSENSITIVE_TEST @Value(_SubdName) CONTAINS_REGEX  [A-Z]+-X
      CASE_INSENSITIVE_TEST @Value(_SubdName) CONTAINS_REGEX  X$",Send Back
    Send Back -> Rom_Num_Dash (output)
    <UNFILTERED> -> Standard_Keyphrases

Bookmark: Rom Num Dash Loop
Rom_Num_Dash (output)

Bookmark: Replace keyphrases with standardized versions for easier handling later
Standard_Keyphrases (input)
    -> Standard_Keyphrases
Standard_Keyphrases: TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_SubdName) CONTAINS_REGEX (^LTS | LTS | LTS$|^LOTS | LOTS | LOTS$)",LOT,"BOOL_OP,OR,COMPOSITE_TEST,""""""1"""""",TEST_CLAUSE,CASE_INSENSITIVE_TEST @Value(_SubdName) CONTAINS_REGEX (^BLOCK | BLOCK | BLOCK$|^BLOCKS | BLOCKS | BLOCKS$)",BLK,"BOOL_OP,OR,COMPOSITE_TEST,""""""1"""""",TEST_CLAUSE,CASE_INSENSITIVE_TEST @Value(_SubdName) CONTAINS_REGEX (^PHASE | PHASE | PHASE$|^PHASES | PHASES | PHASES$)",PH,"BOOL_OP,OR,COMPOSITE_TEST,""""""1"""""",TEST_CLAUSE,CASE_INSENSITIVE_TEST @Value(_SubdName) CONTAINS_REGEX (^ADDITION | ADDITION | ADDITION$|^ADDITIONS | ADDITIONS | ADDITIONS$)",ADDN,"BOOL_OP,OR,COMPOSITE_TEST,""""""1"""""",TEST_CLAUSE,CASE_INSENSITIVE_TEST @Value(_SubdName) CONTAINS_REGEX (^PARCEL | PARCEL | PARCEL$|^PARCELS | PARCELS | PARCELS$)",PAR,"BOOL_OP,OR,COMPOSITE_TEST,""""""1"""""",TEST_CLAUSE,CASE_INSENSITIVE_TEST @Value(_SubdName) CONTAINS_REGEX (^SECTION | SECTION | SECTION$|^SECTIONS | SECTIONS | SECTIONS$|^SECT | SECT | SECT$|^SECTS | SECTS | SECTS$)",SEC,"BOOL_OP,OR,COMPOSITE_TEST,""""""1"""""",TEST_CLAUSE,CASE_INSENSITIVE_TEST @Value(_SubdName) CONTAINS_REGEX (^TRACT | TRACT | TRACT$|^TRACTS | TRACTS | TRACTS$)",TRCT,"BOOL_OP,OR,COMPOSITE_TEST,""""""1"""""",TEST_CLAUSE,CASE_INSENSITIVE_TEST @Value(_SubdName) CONTAINS_REGEX (^REVISED | REVISED | REVISED$|^REVISION | REVISION | REVISION$|^REVISIONS | REVISIONS | REVISIONS$|^RE | RE | RE$|^RES | RES | RES$)",REV,"BOOL_OP,OR,COMPOSITE_TEST,""""""1"""""",TEST_CLAUSE,CASE_INSENSITIVE_TEST @Value(_SubdName) CONTAINS_REGEX (^COND | COND | COND$|^CONDS | CONDS | CONDS$|^CONDO | CONDO | CONDO$|^CONDOS | CONDOS | CONDOS$)",COND,"BOOL_OP,OR,COMPOSITE_TEST,""""""1"""""",TEST_CLAUSE,CASE_INSENSITIVE_TEST @Value(_SubdName) CONTAINS_REGEX (^PT | PT | PT$|^PTS | PTS | PTS$)",PT,"BOOL_OP,OR,COMPOSITE_TEST,""""""1"""""",TEST_CLAUSE,CASE_INSENSITIVE_TEST @Value(_SubdName) CONTAINS_REGEX (^AREAS | AREAS | AREAS$)",AREA
    LOT -> LOT
    BLK -> BLK
    PH -> PH
    ADDN -> ADDN
    PAR -> PAR
    SEC -> SEC
    TRCT -> TRCT
    REV -> REV
    COND -> COND
    PT -> PT
    AREA -> AREA
    <UNFILTERED> -> Clean_Spaces_3
LOT: StringReplacer
    CASE = NO
    FIND_TEXT = (^LTS | LTS | LTS$|^LOTS | LOTS | LOTS$)
    NO_MATCH = _FME_NO_OP_
    REGEXP = YES
    REPLACE_TEXT = " LOT "
    SRC_ATTRS = _SubdName
    -> Check_Standard_Keyphrases_Again
TRCT: StringReplacer
    CASE = NO
    FIND_TEXT = (^TRACT | TRACT | TRACT$|^TRACTS | TRACTS | TRACTS$)
    NO_MATCH = _FME_NO_OP_
    REGEXP = YES
    REPLACE_TEXT = " TRCT "
    SRC_ATTRS = _SubdName
    -> Check_Standard_Keyphrases_Again
BLK: StringReplacer
    CASE = NO
    FIND_TEXT = (^BLOCK | BLOCK | BLOCK$|^BLOCKS | BLOCKS | BLOCKS$)
    NO_MATCH = _FME_NO_OP_
    REGEXP = YES
    REPLACE_TEXT = " BLK "
    SRC_ATTRS = _SubdName
    -> Check_Standard_Keyphrases_Again
REV: StringReplacer
    CASE = NO
    FIND_TEXT = (^REVISED | REVISED | REVISED$|^REVISION | REVISION | REVISION$|^REVISIONS | REVISIONS | REVISIONS$|^RE | RE | RE$|^RES | RES | RES$)
    NO_MATCH = _FME_NO_OP_
    REGEXP = YES
    REPLACE_TEXT = " REV "
    SRC_ATTRS = _SubdName
    -> Check_Standard_Keyphrases_Again
PH: StringReplacer
    CASE = NO
    FIND_TEXT = (^PHASE | PHASE | PHASE$|^PHASES | PHASES | PHASES$)
    NO_MATCH = _FME_NO_OP_
    REGEXP = YES
    REPLACE_TEXT = " PH "
    SRC_ATTRS = _SubdName
    -> Check_Standard_Keyphrases_Again
COND: StringReplacer
    CASE = NO
    FIND_TEXT = (^COND | COND | COND$|^CONDS | CONDS | CONDS$|^CONDO | CONDO | CONDO$|^CONDOS | CONDOS | CONDOS$)
    NO_MATCH = _FME_NO_OP_
    REGEXP = YES
    REPLACE_TEXT = " CONDOMINIUMS "
    SRC_ATTRS = _SubdName
    -> Check_Standard_Keyphrases_Again
ADDN: StringReplacer
    CASE = NO
    FIND_TEXT = (^ADDITION | ADDITION | ADDITION$|^ADDITIONS | ADDITIONS | ADDITIONS$)
    NO_MATCH = _FME_NO_OP_
    REGEXP = YES
    REPLACE_TEXT = " ADDN "
    SRC_ATTRS = _SubdName
    -> Check_Standard_Keyphrases_Again
PT: StringReplacer
    CASE = NO
    FIND_TEXT = (^PT | PT | PT$|^PTS | PTS | PTS$)
    NO_MATCH = _FME_NO_OP_
    REGEXP = YES
    REPLACE_TEXT = " PART "
    SRC_ATTRS = _SubdName
    -> Check_Standard_Keyphrases_Again
PAR: StringReplacer
    CASE = NO
    FIND_TEXT = (^PARCEL | PARCEL | PARCEL$|^PARCELS | PARCELS | PARCELS$)
    NO_MATCH = _FME_NO_OP_
    REGEXP = YES
    REPLACE_TEXT = " PAR "
    SRC_ATTRS = _SubdName
    -> Check_Standard_Keyphrases_Again
AREA: StringReplacer
    CASE = NO
    FIND_TEXT = (^AREAS | AREAS | AREAS$)
    NO_MATCH = _FME_NO_OP_
    REGEXP = YES
    REPLACE_TEXT = " AREA "
    SRC_ATTRS = _SubdName
    -> Check_Standard_Keyphrases_Again
SEC: StringReplacer
    CASE = NO
    FIND_TEXT = (^SECTION | SECTION | SECTION$|^SECTIONS | SECTIONS | SECTIONS$|^SECT | SECT | SECT$|^SECTS | SECTS | SECTS$)
    NO_MATCH = _FME_NO_OP_
    REGEXP = YES
    REPLACE_TEXT = " SEC "
    SRC_ATTRS = _SubdName
    -> Check_Standard_Keyphrases_Again
Check_Standard_Keyphrases_Again: TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_SubdName) CONTAINS_REGEX (^LTS | LTS | LTS$|^LOTS | LOTS | LOTS$)",Send Back,"BOOL_OP,OR,COMPOSITE_TEST,""""""1"""""",TEST_CLAUSE,CASE_INSENSITIVE_TEST @Value(_SubdName) CONTAINS_REGEX (^BLOCK | BLOCK | BLOCK$|^BLOCKS | BLOCKS | BLOCKS$)",Send Back,"BOOL_OP,OR,COMPOSITE_TEST,""""""1"""""",TEST_CLAUSE,CASE_INSENSITIVE_TEST @Value(_SubdName) CONTAINS_REGEX (^PHASE | PHASE | PHASE$|^PHASES | PHASES | PHASES$)",Send Back,"BOOL_OP,OR,COMPOSITE_TEST,""""""1"""""",TEST_CLAUSE,CASE_INSENSITIVE_TEST @Value(_SubdName) CONTAINS_REGEX (^ADDITION | ADDITION | ADDITION$|^ADDITIONS | ADDITIONS | ADDITIONS$)",Send Back,"BOOL_OP,OR,COMPOSITE_TEST,""""""1"""""",TEST_CLAUSE,CASE_INSENSITIVE_TEST @Value(_SubdName) CONTAINS_REGEX (^PARCEL | PARCEL | PARCEL$|^PARCELS | PARCELS | PARCELS$)",Send Back,"BOOL_OP,OR,COMPOSITE_TEST,""""""1"""""",TEST_CLAUSE,CASE_INSENSITIVE_TEST @Value(_SubdName) CONTAINS_REGEX (^SECTION | SECTION | SECTION$|^SECTIONS | SECTIONS | SECTIONS$|^SECT | SECT | SECT$|^SECTS | SECTS | SECTS$)",Send Back,"BOOL_OP,OR,COMPOSITE_TEST,""""""1"""""",TEST_CLAUSE,CASE_INSENSITIVE_TEST @Value(_SubdName) CONTAINS_REGEX (^TRACT | TRACT | TRACT$|^TRACTS | TRACTS | TRACTS$)",Send Back,"BOOL_OP,OR,COMPOSITE_TEST,""""""1"""""",TEST_CLAUSE,CASE_INSENSITIVE_TEST @Value(_SubdName) CONTAINS_REGEX (^REVISED | REVISED | REVISED$|^REVISION | REVISION | REVISION$|^REVISIONS | REVISIONS | REVISIONS$|^RE | RE | RE$|^RES | RES | RES$)",Send Back,"BOOL_OP,OR,COMPOSITE_TEST,""""""1"""""",TEST_CLAUSE,CASE_INSENSITIVE_TEST @Value(_SubdName) CONTAINS_REGEX (^COND | COND | COND$|^CONDS | CONDS | CONDS$|^CONDO | CONDO | CONDO$|^CONDOS | CONDOS | CONDOS$)",Send Back,"BOOL_OP,OR,COMPOSITE_TEST,""""""1"""""",TEST_CLAUSE,CASE_INSENSITIVE_TEST @Value(_SubdName) CONTAINS_REGEX (^PT | PT | PT$|^PTS | PTS | PTS$)",Send Back,"BOOL_OP,OR,COMPOSITE_TEST,""""""1"""""",TEST_CLAUSE,CASE_INSENSITIVE_TEST @Value(_SubdName) CONTAINS_REGEX (^AREAS | AREAS | AREAS$)",Send Back
    Send Back -> Standard_Keyphrases (output)
    <UNFILTERED> -> Clean_Spaces_3

Bookmark: Remove Extra Spaces for _SubdName
Note: Replace double spaces with single spaces
Clean_Spaces_3: StringReplacer
    CASE = NO
    FIND_TEXT = "  "
    NO_MATCH = _FME_NO_OP_
    REGEXP = NO
    REPLACE_TEXT = " "
    SRC_ATTRS = _SubdName
    -> Check_Again_3
Note: Then check to see if any more spaces are found
Check_Again_3: Tester
    BOOL_OP = OR
    TEST_CLAUSE = CASE_INSENSITIVE_TEST @Value(_SubdName) CONTAINS_REGEX
    TEST_MODE = CASE_INSENSITIVE_TEST
    PASSED -> Spaces (output)
    FAILED -> Junction_32
Note: Else, continue...
Junction_32
    -> Output (output)

Bookmark: Double Spaces Loop
Note: If more spaces are found, go back to the beginning
Spaces (output)

Bookmark: Loop to Standard Keyphrases
Standard_Keyphrases (output)

FME custom transformer Subd Name Cleaners
Extracts info from the parcels info text files sent by the Assessor's Office

Parameters:
- TEXT_LINE_DATA = @Value(text_line_data)   # Text Line Data
- _PARCELID = @Value(_ParcelID)   # Parcelid
- _SUBDNAME = @Value(_SubdName)   # Subdname
- FME_PROCESS_GROUP_BY =   # "" Group By
- FME_PROCESS_GROUPS_ORDERED = No   # When All Features Received,No%When Group Changes (Advanced),Yes Complete Groups

Note: Note: This tool uses all UPPER CASE characters. Change to upper case if needed.
Note: Future work: Write detailed description of cleaners, specifically their order
Note: Examples: / " Main St" -----> "Main St" / "Main St" -----> "Main St" / "Main St " -----> "Main St"
Note: Note: the regix expression here are very specific. Be careful when editing them and/or adding new ones
Note: Regex
Input (input)
    -> Clean_Init_Space
Note: Examples: / RE-SUBDIVISION -----> [nothing/remove] / S/D -----> [nothing/remove] / " PART OF " -----> [nothing/remove]
Note: Examples: / 1A & 2B -----> [nothing/remove] / 1 A & 2B -----> [nothing/remove] / 1A&2 B -----> [nothing/remove]
Note: Examples: / PHASE 1 -----> [nothing/remove] / 1ST ADDN -----> [nothing/remove] / PAR 2B -----> [nothing/remove]
Note: Examples: / MAIN ST ADDN -----> [nothing/remove] / MAIN PH ST -----> [nothing/remove] / LOT MAIN ST -----> [nothing/remove]
Note: Examples: / 1-2 -----> [nothing/remove] / B -1 -----> [nothing/remove] / A - C -----> [nothing/remove]
Note: ONLY matching 1 letter characters for text
Note: Examples: / MAIN ST TO -----> [nothing/remove] / THE 2ND MAIN ST -----> [nothing/remove] / MAIN AND B ST -----> [nothing/remove]
Note: Look for double spaces again. If found, sent to start, so the logic can be checked again
Output (output)

Bookmark: Preemptively Remove Extra Spaces
Init_Space (input)
    -> Clean_Init_Space
Clean_Init_Space: StringReplacer
    CASE = NO
    FIND_TEXT = "  "
    NO_MATCH = _FME_NO_OP_
    REGEXP = NO
    REPLACE_TEXT = " "
    SRC_ATTRS = _SubdName,_ParcelID
    -> Tim_at_ends
Tim_at_ends: AttributeTrimmer
    SRC_ATTRS = _SubdName
    TRIM_CHARS = " "
    TRIM_TO_NONE = Yes
    TRIM_TYPE = Both
    -> Check_for_spaces
Check_for_spaces: Tester
    BOOL_OP = OR
    TEST_CLAUSE:
      CASE_INSENSITIVE_TEST @Value(_SubdName) CONTAINS_REGEX
      CASE_INSENSITIVE_TEST @Value(_ParcelID) CONTAINS_REGEX
    TEST_MODE = CASE_INSENSITIVE_TEST
    PASSED -> Init_Space (output)
    FAILED -> Find_Keywords

Bookmark: Initial Space Loop
Init_Space (output)

Bookmark: Remove certain workds that can be safely removed without having to account for order within a string
Keywords_Loop (input)
    -> Find_Keywords
Note: Regex
Find_Keywords: Tester
    BOOL_OP = OR
    TEST_CLAUSE = CASE_INSENSITIVE_TEST @Value(_SubdName) CONTAINS_REGEX (RE-SUBDIVISION|SUBDIVISION|SUBDV|SUBD|RESUB|RE-SUB| RE SUB |P U D| PUD |AMENDMENT|AMEND|AMEN|PD|UNRECORDED|UNREC|REREC|FINAL PLAN|FINAL PLA|OUTLINE PLAN|PROPOSED| P D |^P D | P D$| PT OF |^PT OF | PT OF$| PART OF |^PART OF | PART OF$| SD |^SD | SD$| S/D |^S/D | S/D$| RES |^RES | RES$)
    TEST_MODE = CASE_INSENSITIVE_TEST
    PASSED -> Replace_Keywords
    FAILED -> Junction
Note: Regex
Replace_Keywords: StringReplacer
    CASE = NO
    FIND_TEXT = (RE-SUBDIVISION|SUBDIVISION|SUBDV|SUBD|RESUB|RE-SUB| RE SUB |P U D| PUD |AMENDMENT|AMEND|AMEN|PD|UNRECORDED|UNREC|REREC|FINAL PLAN|FINAL PLA|OUTLINE PLAN|PROPOSED| P D |^P D | P D$| PT OF |^PT OF | PT OF$| PART OF |^PART OF | PART OF$| SD |^SD | SD$| S/D |^S/D | S/D$| RES |^RES | RES$)
    NO_MATCH = _FME_NO_OP_
    REGEXP = YES
    REPLACE_TEXT = " "
    SRC_ATTRS = _SubdName
    -> Search_again
Note: Regex
Search_again: Tester
    BOOL_OP = OR
    TEST_CLAUSE = CASE_INSENSITIVE_TEST @Value(_SubdName) CONTAINS_REGEX (RE-SUBDIVISION|SUBDIVISION|SUBDV|SUBD|RESUB|RE-SUB| RE SUB |P U D| PUD |AMENDMENT|AMEND|AMEN|PD|UNRECORDED|UNREC|REREC|FINAL PLAN|FINAL PLA|OUTLINE PLAN|PROPOSED| P D |^P D | P D$| PT OF |^PT OF | PT OF$| PART OF |^PART OF | PART OF$| SD |^SD | SD$| S/D |^S/D | S/D$| RES |^RES | RES$)
    TEST_MODE = CASE_INSENSITIVE_TEST
    PASSED -> Keywords_Loop (output)
    FAILED -> Junction
Junction
    -> Replace_Double_Ands

Bookmark: Keywords Loop
Keywords_Loop (output)

Bookmark: AND (&) Scenarios
And_Scenarios (input)
    -> Replace_Double_Ands
Replace_Double_Ands: StringReplacer
    CASE = NO
    FIND_TEXT = & &
    NO_MATCH = _FME_NO_OP_
    REGEXP = YES
    REPLACE_TEXT = &
    SRC_ATTRS = _SubdName
    -> Check_for_AND_Scenarios
Note: Regex
Check_for_AND_Scenarios: Tester
    BOOL_OP = OR
    TEST_CLAUSE = CASE_SENSITIVE_TEST @Value(_SubdName) CONTAINS_REGEX (\d+-[A-Z]+ & \d+-[A-Z]+|[A-Z]+-\d+ & [A-Z]+-\d+|\d+[A-Z]+ & \d+[A-Z]+|[A-Z]+\d+ & [A-Z]+\d+|\d+ & \d+| [A-Z] & [A-Z] |\d+-[A-Z]+&\d+-[A-Z]+|[A-Z]+-\d+&[A-Z]+-\d+|\d+[A-Z]+&\d+[A-Z]+|[A-Z]+\d+&[A-Z]+\d+|\d+&\d+| [A-Z]&[A-Z] |\d+-[A-Z]+& \d+-[A-Z]+|[A-Z]+-\d+& [A-Z]+-\d+|\d+[A-Z]+& \d+[A-Z]+|[A-Z]+\d+& [A-Z]+\d+|\d+& \d+| [A-Z]& [A-Z] |\d+-[A-Z]+ &\d+-[A-Z]+|[A-Z]+-\d+ &[A-Z]+-\d+|\d+[A-Z]+ &\d+[A-Z]+|[A-Z]+\d+ &[A-Z]+\d+|\d+ &\d+| [A-Z] &[A-Z] | [A-Z]{1} & [A-Z]{1} |^[A-Z]{1} & [A-Z]{1} | [A-Z]{1} & [A-Z]{1} | [A-Z]{1} & [A-Z]{1}$|^[A-Z]{1}& [A-Z]{1} | [A-Z]{1}& [A-Z]{1} | [A-Z]{1}& [A-Z]{1}$|^[A-Z]{1} &[A-Z]{1} | [A-Z]{1} &[A-Z]{1} | [A-Z]{1} &[A-Z]{1}$|^[A-Z]{1}&[A-Z]{1} | [A-Z]{1}&[A-Z]{1} | [A-Z]{1}&[A-Z]{1}$)
    TEST_MODE = CASE_SENSITIVE_TEST
    PASSED -> Replace_AND_Scenarios
    FAILED -> Junction_4
Note: Regex
Replace_AND_Scenarios: StringReplacer
    CASE = NO
    FIND_TEXT = (\d+-[A-Z]+ & \d+-[A-Z]+|[A-Z]+-\d+ & [A-Z]+-\d+|\d+[A-Z]+ & \d+[A-Z]+|[A-Z]+\d+ & [A-Z]+\d+|\d+ & \d+| [A-Z] & [A-Z] |\d+-[A-Z]+&\d+-[A-Z]+|[A-Z]+-\d+&[A-Z]+-\d+|\d+[A-Z]+&\d+[A-Z]+|[A-Z]+\d+&[A-Z]+\d+|\d+&\d+| [A-Z]&[A-Z] |\d+-[A-Z]+& \d+-[A-Z]+|[A-Z]+-\d+& [A-Z]+-\d+|\d+[A-Z]+& \d+[A-Z]+|[A-Z]+\d+& [A-Z]+\d+|\d+& \d+| [A-Z]& [A-Z] |\d+-[A-Z]+ &\d+-[A-Z]+|[A-Z]+-\d+ &[A-Z]+-\d+|\d+[A-Z]+ &\d+[A-Z]+|[A-Z]+\d+ &[A-Z]+\d+|\d+ &\d+| [A-Z] &[A-Z] | [A-Z]{1} & [A-Z]{1} |^[A-Z]{1} & [A-Z]{1} | [A-Z]{1} & [A-Z]{1} | [A-Z]{1} & [A-Z]{1}$|^[A-Z]{1}& [A-Z]{1} | [A-Z]{1}& [A-Z]{1} | [A-Z]{1}& [A-Z]{1}$|^[A-Z]{1} &[A-Z]{1} | [A-Z]{1} &[A-Z]{1} | [A-Z]{1} &[A-Z]{1}$|^[A-Z]{1}&[A-Z]{1} | [A-Z]{1}&[A-Z]{1} | [A-Z]{1}&[A-Z]{1}$)
    NO_MATCH = _FME_NO_OP_
    REGEXP = YES
    REPLACE_TEXT = " "
    SRC_ATTRS = _SubdName
    -> Check_for_AND_Scenarios_Again
Note: Regex
Check_for_AND_Scenarios_Again: Tester
    BOOL_OP = OR
    TEST_CLAUSE = CASE_SENSITIVE_TEST @Value(_SubdName) CONTAINS_REGEX (\d+-[A-Z]+ & \d+-[A-Z]+|[A-Z]+-\d+ & [A-Z]+-\d+|\d+[A-Z]+ & \d+[A-Z]+|[A-Z]+\d+ & [A-Z]+\d+|\d+ & \d+| [A-Z] & [A-Z] |\d+-[A-Z]+&\d+-[A-Z]+|[A-Z]+-\d+&[A-Z]+-\d+|\d+[A-Z]+&\d+[A-Z]+|[A-Z]+\d+&[A-Z]+\d+|\d+&\d+| [A-Z]&[A-Z] |\d+-[A-Z]+& \d+-[A-Z]+|[A-Z]+-\d+& [A-Z]+-\d+|\d+[A-Z]+& \d+[A-Z]+|[A-Z]+\d+& [A-Z]+\d+|\d+& \d+| [A-Z]& [A-Z] |\d+-[A-Z]+ &\d+-[A-Z]+|[A-Z]+-\d+ &[A-Z]+-\d+|\d+[A-Z]+ &\d+[A-Z]+|[A-Z]+\d+ &[A-Z]+\d+|\d+ &\d+| [A-Z] &[A-Z] | [A-Z]{1} & [A-Z]{1} |^[A-Z]{1} & [A-Z]{1} | [A-Z]{1} & [A-Z]{1} | [A-Z]{1} & [A-Z]{1}$|^[A-Z]{1}& [A-Z]{1} | [A-Z]{1}& [A-Z]{1} | [A-Z]{1}& [A-Z]{1}$|^[A-Z]{1} &[A-Z]{1} | [A-Z]{1} &[A-Z]{1} | [A-Z]{1} &[A-Z]{1}$|^[A-Z]{1}&[A-Z]{1} | [A-Z]{1}&[A-Z]{1} | [A-Z]{1}&[A-Z]{1}$)
    TEST_MODE = CASE_SENSITIVE_TEST
    PASSED -> And_Scenarios (output)
    FAILED -> Junction_4
Junction_4
    -> Check_for_Standard_Scenarios

Bookmark: AND Scenarios Loop
And_Scenarios (output)

Bookmark: Standard Scenarios
StandardKeywords_Loop (input)
    -> Check_for_Standard_Scenarios
Note: Regex
Check_for_Standard_Scenarios: Tester
    BOOL_OP = OR
    TEST_CLAUSE = CASE_INSENSITIVE_TEST @Value(_SubdName) CONTAINS_REGEX ([0-9]+[A-Z]+ ADDN| ADDN [0-9]+-[A-Z]+| ADDN [0-9]+[A-Z]+| ADDN [A-Z]{1} | ADDN [0-9]+| ADDN [A-Z]+-[0-9]+| ADDN [A-Z]+[0-9]+| ADDN [A-Z]$| BLK [0-9]+-[A-Z]+| BLK [A-Z]+-[0-9]+| BLK [0-9]+[A-Z]+| BLK [A-Z]+[0-9]+| BLK [A-Z]{1} | BLK [0-9]+| BLK [A-Z]$| PH [0-9]+-[A-Z]+| PH [A-Z]+-[0-9]+| PH [0-9]+[A-Z]+| PH [A-Z]+[0-9]+| PH [0-9]+| PH[0-9]+| PH [A-Z]{1}| PH [A-Z]$ | REV [0-9]+-[A-Z]+| REV [A-Z]+-[0-9]+| REV [0-9]+[A-Z]+| REV [A-Z]+[0-9]+| REV [0-9]+| REV [A-Z]{1} | REV [A-Z]$| SEC [0-9]+-[A-Z]+| SEC [A-Z]+-[0-9]+| SEC [0-9]+[A-Z]+| SEC [A-Z]+[0-9]+| SEC [0-9]+| SEC [A-Z]{1} | SEC [A-Z]$| LOT [0-9]+-[A-Z]+| LOT [A-Z]+-[0-9]+| LOT [0-9]+[A-Z]+| LOT [A-Z]+[0-9]+| LOT [0-9]+| LOT [A-Z]{1} | LOT [A-Z]$| PAR [0-9]+-[A-Z]+| PAR [A-Z]+-[0-9]+| PAR [0-9]+[A-Z]+| PAR [A-Z]+[0-9]+| PAR [0-9]+| PAR [A-Z]{1} | PAR [A-Z]$| TWP [0-9]+-[A-Z]+| TWP [A-Z]+-[0-9]+| TWP [0-9]+[A-Z]+| TWP [A-Z]+[0-9]+| TWP [0-9]+| TWP [A-Z]{1} | TWP [A-Z]$| TRCT [0-9]+-[A-Z]+| TRCT [A-Z]+-[0-9]+| TRCT [0-9]+[A-Z]+| TRCT [A-Z]+[0-9]+| TRCT [0-9]+| TRCT [A-Z]{1} | TRCT [A-Z]$| AREA [0-9]+-[A-Z]+| AREA [A-Z]+-[0-9]+| AREA [0-9]+[A-Z]+| AREA [A-Z]+[0-9]+| AREA [0-9]+| AREA [A-Z]{1} | AREA [A-Z]$| PART [0-9]+-[A-Z]+| PART [A-Z]+-[0-9]+| PART [0-9]+[A-Z]+| PART [A-Z]+[0-9]+| PART [0-9]+| PART [A-Z]{1} | PART [A-Z]$)
    TEST_MODE = CASE_INSENSITIVE_TEST
    PASSED -> Replace_Standard_Scenarios
    FAILED -> Junction_6
Note: Regex
Replace_Standard_Scenarios: StringReplacer
    CASE = NO
    FIND_TEXT = ([0-9]+[A-Z]+ ADDN| ADDN [0-9]+-[A-Z]+| ADDN [0-9]+[A-Z]+| ADDN [A-Z]{1} | ADDN [0-9]+| ADDN [A-Z]+-[0-9]+| ADDN [A-Z]+[0-9]+| ADDN [A-Z]$| BLK [0-9]+-[A-Z]+| BLK [A-Z]+-[0-9]+| BLK [0-9]+[A-Z]+| BLK [A-Z]+[0-9]+| BLK [A-Z]{1} | BLK [0-9]+| BLK [A-Z]$| PH [0-9]+-[A-Z]+| PH [A-Z]+-[0-9]+| PH [0-9]+[A-Z]+| PH [A-Z]+[0-9]+| PH [0-9]+| PH[0-9]+| PH [A-Z]{1}| PH [A-Z]$ | REV [0-9]+-[A-Z]+| REV [A-Z]+-[0-9]+| REV [0-9]+[A-Z]+| REV [A-Z]+[0-9]+| REV [0-9]+| REV [A-Z]{1} | REV [A-Z]$| SEC [0-9]+-[A-Z]+| SEC [A-Z]+-[0-9]+| SEC [0-9]+[A-Z]+| SEC [A-Z]+[0-9]+| SEC [0-9]+| SEC [A-Z]{1} | SEC [A-Z]$| LOT [0-9]+-[A-Z]+| LOT [A-Z]+-[0-9]+| LOT [0-9]+[A-Z]+| LOT [A-Z]+[0-9]+| LOT [0-9]+| LOT [A-Z]{1} | LOT [A-Z]$| PAR [0-9]+-[A-Z]+| PAR [A-Z]+-[0-9]+| PAR [0-9]+[A-Z]+| PAR [A-Z]+[0-9]+| PAR [0-9]+| PAR [A-Z]{1} | PAR [A-Z]$| TWP [0-9]+-[A-Z]+| TWP [A-Z]+-[0-9]+| TWP [0-9]+[A-Z]+| TWP [A-Z]+[0-9]+| TWP [0-9]+| TWP [A-Z]{1} | TWP [A-Z]$| TRCT [0-9]+-[A-Z]+| TRCT [A-Z]+-[0-9]+| TRCT [0-9]+[A-Z]+| TRCT [A-Z]+[0-9]+| TRCT [0-9]+| TRCT [A-Z]{1} | TRCT [A-Z]$| AREA [0-9]+-[A-Z]+| AREA [A-Z]+-[0-9]+| AREA [0-9]+[A-Z]+| AREA [A-Z]+[0-9]+| AREA [0-9]+| AREA [A-Z]{1} | AREA [A-Z]$| PART [0-9]+-[A-Z]+| PART [A-Z]+-[0-9]+| PART [0-9]+[A-Z]+| PART [A-Z]+[0-9]+| PART [0-9]+| PART [A-Z]{1} | PART [A-Z]$)
    NO_MATCH = _FME_NO_OP_
    REGEXP = YES
    REPLACE_TEXT = " "
    SRC_ATTRS = _SubdName
    -> Check_for_Standard_Scenarios_Again
Note: Regex
Check_for_Standard_Scenarios_Again: Tester
    BOOL_OP = OR
    TEST_CLAUSE = CASE_INSENSITIVE_TEST @Value(_SubdName) CONTAINS_REGEX ([0-9]+[A-Z]+ ADDN| ADDN [0-9]+-[A-Z]+| ADDN [0-9]+[A-Z]+| ADDN [A-Z]{1} | ADDN [0-9]+| ADDN [A-Z]+-[0-9]+| ADDN [A-Z]+[0-9]+| ADDN [A-Z]$| BLK [0-9]+-[A-Z]+| BLK [A-Z]+-[0-9]+| BLK [0-9]+[A-Z]+| BLK [A-Z]+[0-9]+| BLK [A-Z]{1} | BLK [0-9]+| BLK [A-Z]$| PH [0-9]+-[A-Z]+| PH [A-Z]+-[0-9]+| PH [0-9]+[A-Z]+| PH [A-Z]+[0-9]+| PH [0-9]+| PH[0-9]+| PH [A-Z]{1}| PH [A-Z]$ | REV [0-9]+-[A-Z]+| REV [A-Z]+-[0-9]+| REV [0-9]+[A-Z]+| REV [A-Z]+[0-9]+| REV [0-9]+| REV [A-Z]{1} | REV [A-Z]$| SEC [0-9]+-[A-Z]+| SEC [A-Z]+-[0-9]+| SEC [0-9]+[A-Z]+| SEC [A-Z]+[0-9]+| SEC [0-9]+| SEC [A-Z]{1} | SEC [A-Z]$| LOT [0-9]+-[A-Z]+| LOT [A-Z]+-[0-9]+| LOT [0-9]+[A-Z]+| LOT [A-Z]+[0-9]+| LOT [0-9]+| LOT [A-Z]{1} | LOT [A-Z]$| PAR [0-9]+-[A-Z]+| PAR [A-Z]+-[0-9]+| PAR [0-9]+[A-Z]+| PAR [A-Z]+[0-9]+| PAR [0-9]+| PAR [A-Z]{1} | PAR [A-Z]$| TWP [0-9]+-[A-Z]+| TWP [A-Z]+-[0-9]+| TWP [0-9]+[A-Z]+| TWP [A-Z]+[0-9]+| TWP [0-9]+| TWP [A-Z]{1} | TWP [A-Z]$| TRCT [0-9]+-[A-Z]+| TRCT [A-Z]+-[0-9]+| TRCT [0-9]+[A-Z]+| TRCT [A-Z]+[0-9]+| TRCT [0-9]+| TRCT [A-Z]{1} | TRCT [A-Z]$| AREA [0-9]+-[A-Z]+| AREA [A-Z]+-[0-9]+| AREA [0-9]+[A-Z]+| AREA [A-Z]+[0-9]+| AREA [0-9]+| AREA [A-Z]{1} | AREA [A-Z]$| PART [0-9]+-[A-Z]+| PART [A-Z]+-[0-9]+| PART [0-9]+[A-Z]+| PART [A-Z]+[0-9]+| PART [0-9]+| PART [A-Z]{1} | PART [A-Z]$)
    TEST_MODE = CASE_INSENSITIVE_TEST
    PASSED -> StandardKeywords_Loop (output)
    FAILED -> Junction_6
Junction_6
    -> Check_for_Trim_Scenarios

Bookmark: Keywords Scenarios Loop
StandardKeywords_Loop (output)

Bookmark: Trim Scenarios
Trim_Loop (input)
    -> Check_for_Trim_Scenarios
Note: Regex
Check_for_Trim_Scenarios: Tester
    BOOL_OP = OR
    TEST_CLAUSE = CASE_INSENSITIVE_TEST @Value(_SubdName) CONTAINS_REGEX (^ADDN | ADDN | ADDN$|^BLK | BLK | BLK$|^PH | PH | PH$|^REV | REV | REV$|^SEC | SEC | SEC$|^LOT | LOT | LOT$|^TWP | TWP | TWP$|^TRCT | TRCT | TRCT$|^AREA | AREA | AREA$|^PAR | PAR | PAR$)
    TEST_MODE = CASE_INSENSITIVE_TEST
    PASSED -> Replace_Trim_Scenarios
    FAILED -> Junction_7
Note: Regex
Replace_Trim_Scenarios: StringReplacer
    CASE = NO
    FIND_TEXT = (^ADDN | ADDN | ADDN$|^BLK | BLK | BLK$|^PH | PH | PH$|^REV | REV | REV$|^SEC | SEC | SEC$|^LOT | LOT | LOT$|^TWP | TWP | TWP$|^TRCT | TRCT | TRCT$|^AREA | AREA | AREA$|^PAR | PAR | PAR$)
    NO_MATCH = _FME_NO_OP_
    REGEXP = YES
    REPLACE_TEXT = " "
    SRC_ATTRS = _SubdName
    -> Check_for_Trim_Scenarios_Again
Note: Regex
Check_for_Trim_Scenarios_Again: Tester
    BOOL_OP = OR
    TEST_CLAUSE = CASE_INSENSITIVE_TEST @Value(_SubdName) CONTAINS_REGEX (^ADDN | ADDN | ADDN$|^BLK | BLK | BLK$|^PH | PH | PH$|^REV | REV | REV$|^SEC | SEC | SEC$|^LOT | LOT | LOT$|^TWP | TWP | TWP$|^TRCT | TRCT | TRCT$|^AREA | AREA | AREA$|^PAR | PAR | PAR$)
    TEST_MODE = CASE_INSENSITIVE_TEST
    PASSED -> Trim_Loop (output)
    FAILED -> Junction_7
Junction_7
    -> Check_for_Dash_Scenarios

Bookmark: Trim Loop
Trim_Loop (output)

Bookmark: Dash (-) Scenarios
Dash_Scenarios (input)
    -> Check_for_Dash_Scenarios
Note: Regex
Check_for_Dash_Scenarios: Tester
    BOOL_OP = OR
    TEST_CLAUSE = CASE_INSENSITIVE_TEST @Value(_SubdName) CONTAINS_REGEX (^[\d]+-[\d]+ | [\d]+-[\d]+ | [\d]+-[\d]+$|^[\d]+ - [\d]+ | [\d]+ - [\d]+ | [\d]+ - [\d]+$|^[\d]+ -[\d]+ | [\d]+ -[\d]+ | [\d]+ -[\d]+$|^[\d]+- [\d]+ | [\d]+- [\d]+ | [\d]+- [\d]+$|^[\d]+- | [\d]+- | [\d]+-$|^[\d]+ - | [\d]+ - | [\d]+ -$|^-[\d]+ | -[\d]+ | -[\d]+$|^- [\d]+ | - [\d]+ | - [\d]+$|^[A-Z]{1}-[A-Z]{1} | [A-Z]{1}-[A-Z]{1} | [A-Z]{1}-[A-Z]{1}$|^[A-Z]{1} - [A-Z]{1} | [A-Z]{1} - [A-Z]{1} | [A-Z]{1} - [A-Z]{1}$|^[A-Z]{1} -[A-Z]{1} | [A-Z]{1} -[A-Z]{1} | [A-Z]{1} -[A-Z]{1}$|^[A-Z]{1}- [A-Z]{1} | [A-Z]{1}- [A-Z]{1} | [A-Z]{1}- [A-Z]{1}$|^[A-Z]{1}- | [A-Z]{1}- | [A-Z]{1}-$|^[A-Z]{1} - | [A-Z]{1} - | [A-Z]{1} -$|^-[A-Z]{1} | -[A-Z]{1} | -[A-Z]{1}$|^- [A-Z]{1} | - [A-Z]{1} | - [A-Z]{1}$|^[\d]+-[A-Z]{1} | [\d]+-[A-Z]{1} | [\d]+-[A-Z]{1}$|^[\d]+ - [A-Z]{1} | [\d]+ - [A-Z]{1} | [\d]+ - [A-Z]{1}$|^[\d]+ -[A-Z]{1} | [\d]+ -[A-Z]{1} | [\d]+ -[A-Z]{1}$|^[\d]+- [A-Z]{1} | [\d]+- [A-Z]{1} | [\d]+- [A-Z]{1}$|^[A-Z]{1}-[\d]+ | [A-Z]{1}-[\d]+ | [A-Z]{1}-[\d]+$|^[A-Z]{1} - [\d]+ | [A-Z]{1} - [\d]+ | [A-Z]{1} - [\d]+$|^[A-Z]{1} -[\d]+ | [A-Z]{1} -[\d]+ | [A-Z]{1} -[\d]+$|^[A-Z]{1}- [\d]+ | [A-Z]{1}- [\d]+ | [A-Z]{1}- [\d]+$)
    TEST_MODE = CASE_INSENSITIVE_TEST
    PASSED -> Replace_Dash_Scenarios
    FAILED -> Junction_5
Note: Regex
Replace_Dash_Scenarios: StringReplacer
    CASE = NO
    FIND_TEXT = (^[\d]+-[\d]+ | [\d]+-[\d]+ | [\d]+-[\d]+$|^[\d]+ - [\d]+ | [\d]+ - [\d]+ | [\d]+ - [\d]+$|^[\d]+ -[\d]+ | [\d]+ -[\d]+ | [\d]+ -[\d]+$|^[\d]+- [\d]+ | [\d]+- [\d]+ | [\d]+- [\d]+$|^[\d]+- | [\d]+- | [\d]+-$|^[\d]+ - | [\d]+ - | [\d]+ -$|^-[\d]+ | -[\d]+ | -[\d]+$|^- [\d]+ | - [\d]+ | - [\d]+$|^[A-Z]{1}-[A-Z]{1} | [A-Z]{1}-[A-Z]{1} | [A-Z]{1}-[A-Z]{1}$|^[A-Z]{1} - [A-Z]{1} | [A-Z]{1} - [A-Z]{1} | [A-Z]{1} - [A-Z]{1}$|^[A-Z]{1} -[A-Z]{1} | [A-Z]{1} -[A-Z]{1} | [A-Z]{1} -[A-Z]{1}$|^[A-Z]{1}- [A-Z]{1} | [A-Z]{1}- [A-Z]{1} | [A-Z]{1}- [A-Z]{1}$|^[A-Z]{1}- | [A-Z]{1}- | [A-Z]{1}-$|^[A-Z]{1} - | [A-Z]{1} - | [A-Z]{1} -$|^-[A-Z]{1} | -[A-Z]{1} | -[A-Z]{1}$|^- [A-Z]{1} | - [A-Z]{1} | - [A-Z]{1}$|^[\d]+-[A-Z]{1} | [\d]+-[A-Z]{1} | [\d]+-[A-Z]{1}$|^[\d]+ - [A-Z]{1} | [\d]+ - [A-Z]{1} | [\d]+ - [A-Z]{1}$|^[\d]+ -[A-Z]{1} | [\d]+ -[A-Z]{1} | [\d]+ -[A-Z]{1}$|^[\d]+- [A-Z]{1} | [\d]+- [A-Z]{1} | [\d]+- [A-Z]{1}$|^[A-Z]{1}-[\d]+ | [A-Z]{1}-[\d]+ | [A-Z]{1}-[\d]+$|^[A-Z]{1} - [\d]+ | [A-Z]{1} - [\d]+ | [A-Z]{1} - [\d]+$|^[A-Z]{1} -[\d]+ | [A-Z]{1} -[\d]+ | [A-Z]{1} -[\d]+$|^[A-Z]{1}- [\d]+ | [A-Z]{1}- [\d]+ | [A-Z]{1}- [\d]+$)
    NO_MATCH = _FME_NO_OP_
    REGEXP = YES
    REPLACE_TEXT = " "
    SRC_ATTRS = _SubdName
    -> Check_for_Dash_Scenarios_Again
Note: Regex
Check_for_Dash_Scenarios_Again: Tester
    BOOL_OP = OR
    TEST_CLAUSE = CASE_INSENSITIVE_TEST @Value(_SubdName) CONTAINS_REGEX (^[\d]+-[\d]+ | [\d]+-[\d]+ | [\d]+-[\d]+$|^[\d]+ - [\d]+ | [\d]+ - [\d]+ | [\d]+ - [\d]+$|^[\d]+ -[\d]+ | [\d]+ -[\d]+ | [\d]+ -[\d]+$|^[\d]+- [\d]+ | [\d]+- [\d]+ | [\d]+- [\d]+$|^[\d]+- | [\d]+- | [\d]+-$|^[\d]+ - | [\d]+ - | [\d]+ -$|^-[\d]+ | -[\d]+ | -[\d]+$|^- [\d]+ | - [\d]+ | - [\d]+$|^[A-Z]{1}-[A-Z]{1} | [A-Z]{1}-[A-Z]{1} | [A-Z]{1}-[A-Z]{1}$|^[A-Z]{1} - [A-Z]{1} | [A-Z]{1} - [A-Z]{1} | [A-Z]{1} - [A-Z]{1}$|^[A-Z]{1} -[A-Z]{1} | [A-Z]{1} -[A-Z]{1} | [A-Z]{1} -[A-Z]{1}$|^[A-Z]{1}- [A-Z]{1} | [A-Z]{1}- [A-Z]{1} | [A-Z]{1}- [A-Z]{1}$|^[A-Z]{1}- | [A-Z]{1}- | [A-Z]{1}-$|^[A-Z]{1} - | [A-Z]{1} - | [A-Z]{1} -$|^-[A-Z]{1} | -[A-Z]{1} | -[A-Z]{1}$|^- [A-Z]{1} | - [A-Z]{1} | - [A-Z]{1}$|^[\d]+-[A-Z]{1} | [\d]+-[A-Z]{1} | [\d]+-[A-Z]{1}$|^[\d]+ - [A-Z]{1} | [\d]+ - [A-Z]{1} | [\d]+ - [A-Z]{1}$|^[\d]+ -[A-Z]{1} | [\d]+ -[A-Z]{1} | [\d]+ -[A-Z]{1}$|^[\d]+- [A-Z]{1} | [\d]+- [A-Z]{1} | [\d]+- [A-Z]{1}$|^[A-Z]{1}-[\d]+ | [A-Z]{1}-[\d]+ | [A-Z]{1}-[\d]+$|^[A-Z]{1} - [\d]+ | [A-Z]{1} - [\d]+ | [A-Z]{1} - [\d]+$|^[A-Z]{1} -[\d]+ | [A-Z]{1} -[\d]+ | [A-Z]{1} -[\d]+$|^[A-Z]{1}- [\d]+ | [A-Z]{1}- [\d]+ | [A-Z]{1}- [\d]+$)
    TEST_MODE = CASE_INSENSITIVE_TEST
    PASSED -> Dash_Scenarios (output)
    FAILED -> Junction_5
Junction_5
    -> Remant_Keyphrases

Bookmark: Dash Scenarios Loop
Dash_Scenarios (output)

Bookmark: Remove keyphases that may be left behind after all cleanups are done
Remant_Keyphrases (input)
    -> Remant_Keyphrases
Note: Regex
Note: Order matters. Start with longer phrases and whittle them down to the individual words as necessary
Remant_Keyphrases: TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_SubdName) CONTAINS_REGEX ( OF [A-Z]{1} |^OF | OF$)",OF Scenarios,"BOOL_OP,OR,COMPOSITE_TEST,""""""1"""""",TEST_CLAUSE,CASE_INSENSITIVE_TEST @Value(_SubdName) CONTAINS_REGEX ( TO [A-Z]{2} | TO [A-Z]{3} |^TO | TO$)",TO Scenarios,"BOOL_OP,OR,COMPOSITE_TEST,""""""1"""""",TEST_CLAUSE,CASE_INSENSITIVE_TEST @Value(_SubdName) CONTAINS_REGEX ( AND [0-9]+| AND \w{1} |^AND | AND$)",AND Scenarios,"BOOL_OP,OR,COMPOSITE_TEST,""""""1"""""",TEST_CLAUSE,CASE_INSENSITIVE_TEST @Value(_SubdName) CONTAINS_REGEX (^TO THE | TO THE$)",TO THE Scenarios,"BOOL_OP,OR,COMPOSITE_TEST,""""""1"""""",TEST_CLAUSE,CASE_INSENSITIVE_TEST @Value(_SubdName) CONTAINS_REGEX (^OF THE | OF THE$)",OF THE Scenarios,"BOOL_OP,OR,COMPOSITE_TEST,""""""1"""""",TEST_CLAUSE,CASE_INSENSITIVE_TEST @Value(_SubdName) CONTAINS_REGEX ( THE$| THE [0-9][A-Z]{2}$)",THE Scenarios,"BOOL_OP,OR,COMPOSITE_TEST,""""""1"""""",TEST_CLAUSE,CASE_INSENSITIVE_TEST @Value(_SubdName) CONTAINS_REGEX (^[0-9]+[A-Z]{2} | [0-9]+[A-Z]{2}$)",NumTh Scenarios
    OF Scenarios -> OF
    TO Scenarios -> TO
    AND Scenarios -> AND
    TO THE Scenarios -> TO_THE
    OF THE Scenarios -> OF_THE
    THE Scenarios -> THE
    NumTh Scenarios -> 1st_2nd_3rd
    <UNFILTERED> -> Check_All_Again
Note: (^TO THE | TO THE$)
Note: (^OF THE | OF THE$)
Note: ( OF [A-Z]{1} |^OF | OF$)
Note: ( TO [A-Z]{2} | TO [A-Z]{3} |^TO | TO$)
Note: ( AND [0-9]+| AND \w{1} |^AND | AND$)
Note: ( THE$| THE [0-9][A-Z]{2}$)
Note: (^[0-9]+[A-Z]{2} | [0-9]+[A-Z]{2}$)
Note: A valid exception that was omitted here is the phrase "OF IT" because it's very unlikely that it will ever be used in a dataset like this
Note: Regex
Send_Back_RK: TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_SubdName) CONTAINS_REGEX ( OF [A-Z]{1} |^OF | OF$)",Send Back,"BOOL_OP,OR,COMPOSITE_TEST,""""""1"""""",TEST_CLAUSE,CASE_INSENSITIVE_TEST @Value(_SubdName) CONTAINS_REGEX ( TO [A-Z]{2} | TO [A-Z]{3} |^TO | TO$)",Send Back,"BOOL_OP,OR,COMPOSITE_TEST,""""""1"""""",TEST_CLAUSE,CASE_INSENSITIVE_TEST @Value(_SubdName) CONTAINS_REGEX ^AND ",Send Back,"BOOL_OP,OR,COMPOSITE_TEST,""""""1"""""",TEST_CLAUSE,CASE_INSENSITIVE_TEST @Value(_SubdName) CONTAINS_REGEX  AND$",Send Back,"BOOL_OP,OR,COMPOSITE_TEST,""""""1"""""",TEST_CLAUSE,CASE_INSENSITIVE_TEST @Value(_SubdName) CONTAINS_REGEX ^TO THE ",Send Back,"BOOL_OP,OR,COMPOSITE_TEST,""""""1"""""",TEST_CLAUSE,CASE_INSENSITIVE_TEST @Value(_SubdName) CONTAINS_REGEX  TO THE$",Send Back,"BOOL_OP,OR,COMPOSITE_TEST,""""""1"""""",TEST_CLAUSE,CASE_INSENSITIVE_TEST @Value(_SubdName) CONTAINS_REGEX  THE$",Send Back,"BOOL_OP,OR,COMPOSITE_TEST,""""""1"""""",TEST_CLAUSE,CASE_INSENSITIVE_TEST @Value(_SubdName) CONTAINS_REGEX [0-9]+[A-Z]{2}$",Send Back,"BOOL_OP,OR,COMPOSITE_TEST,""""""1"""""",TEST_CLAUSE,CASE_INSENSITIVE_TEST @Value(_SubdName) CONTAINS_REGEX ^[0-9]+[A-Z]{2} ",Send Back
    Send Back -> Remant_Keyphrases (output)
    <UNFILTERED> -> Check_All_Again

Bookmark: Replacers
TO_THE: StringReplacer
    CASE = NO
    FIND_TEXT = (^TO THE | TO THE$)
    NO_MATCH = _FME_NO_OP_
    REGEXP = YES
    REPLACE_TEXT = " "
    SRC_ATTRS = _SubdName
    -> Send_Back_RK
OF_THE: StringReplacer
    CASE = NO
    FIND_TEXT = (^OF THE | OF THE$)
    NO_MATCH = _FME_NO_OP_
    REGEXP = YES
    REPLACE_TEXT = " "
    SRC_ATTRS = _SubdName
    -> Send_Back_RK
OF: StringReplacer
    CASE = NO
    FIND_TEXT = ( OF [A-Z]{1} |^OF | OF$)
    NO_MATCH = _FME_NO_OP_
    REGEXP = YES
    REPLACE_TEXT = " "
    SRC_ATTRS = _SubdName
    -> Send_Back_RK
TO: StringReplacer
    CASE = NO
    FIND_TEXT = ( TO [A-Z]{2} | TO [A-Z]{3} |^TO | TO$)
    NO_MATCH = _FME_NO_OP_
    REGEXP = YES
    REPLACE_TEXT = " "
    SRC_ATTRS = _SubdName
    -> Send_Back_RK
AND: StringReplacer
    CASE = NO
    FIND_TEXT = ( AND [0-9]+| AND \w{1} |^AND | AND$)
    NO_MATCH = _FME_NO_OP_
    REGEXP = YES
    REPLACE_TEXT = " "
    SRC_ATTRS = _SubdName
    -> Send_Back_RK
THE: StringReplacer
    CASE = NO
    FIND_TEXT = ( THE$| THE [0-9][A-Z]{2}$)
    NO_MATCH = _FME_NO_OP_
    REGEXP = YES
    REPLACE_TEXT = " "
    SRC_ATTRS = _SubdName
    -> Send_Back_RK
1st_2nd_3rd: StringReplacer
    CASE = NO
    FIND_TEXT = (^[0-9]+[A-Z]{2} | [0-9]+[A-Z]{2}$)
    NO_MATCH = _FME_NO_OP_
    REGEXP = YES
    REPLACE_TEXT = " "
    SRC_ATTRS = _SubdName
    -> Send_Back_RK

Bookmark: Check all scenarios again
Note: !! IMPORTANT !! / All ReGex changes made to any of the transformers in marked with RED will need to be replicated here. Else an endless loop may occur.
Note: Regex expression to check EVERYTHING again: / (RE-SUBDIVISION|SUBDIVISION|SUBDV|SUBD|RESUB|RE-SUB| RE SUB |P U D| PUD |AMENDMENT|AMEND|AMEN|PD|UNRECORDED|UNREC|REREC|FINAL PLAN|FINAL PLA|OUTLINE PLAN|PROPOSED| P D |^P D | P D$| PT OF |^PT OF | PT OF$| PART OF |^PART OF | PART OF$| SD |^SD | SD$| S/D |^S/D | S/D$| RES |^RES | RES$|\d+-[A-Z]+ & \d+-[A-Z]+|[A-Z]+-\d+ & [A-Z]+-\d+|\d+[A-Z]+ & \d+[A-Z]+|[A-Z]+\d+ & [A-Z]+\d+|\d+ & \d+| [A-Z] & [A-Z] |\d+-[A-Z]+&\d+-[A-Z]+|[A-Z]+-\d+&[A-Z]+-\d+|\d+[A-Z]+&\d+[A-Z]+|[A-Z]+\d+&[A-Z]+\d+|\d+&\d+| [A-Z]&[A-Z] |\d+-[A-Z]+& \d+-[A-Z]+|[A-Z]+-\d+& [A-Z]+-\d+|\d+[A-Z]+& \d+[A-Z]+|[A-Z]+\d+& [A-Z]+\d+|\d+& \d+| [A-Z]& [A-Z] |\d+-[A-Z]+ &\d+-[A-Z]+|[A-Z]+-\d+ &[A-Z]+-\d+|\d+[A-Z]+ &\d+[A-Z]+|[A-Z]+\d+ &[A-Z]+\d+|\d+ &\d+| [A-Z] &[A-Z] | [A-Z]{1} & [A-Z]{1} |^[A-Z]{1} & [A-Z]{1} | [A-Z]{1} & [A-Z]{1} | [A-Z]{1} & [A-Z]{1}$|^[A-Z]{1}& [A-Z]{1} | [A-Z]{1}& [A-Z]{1} | [A-Z]{1}& [A-Z]{1}$|^[A-Z]{1} &[A-Z]{1} | [A-Z]{1} &[A-Z]{1} | [A-Z]{1} &[A-Z]{1}$|^[A-Z]{1}&[A-Z]{1} | [A-Z]{1}&[A-Z]{1} | [A-Z]{1}&[A-Z]{1}$|^[\d]+-[\d]+ | [\d]+-[\d]+ | [\d]+-[\d]+$|^[\d]+ - [\d]+ | [\d]+ - [\d]+ | [\d]+ - [\d]+$|^[\d]+ -[\d]+ | [\d]+ -[\d]+ | [\d]+ -[\d]+$|^[\d]+- [\d]+ | [\d]+- [\d]+ | [\d]+- [\d]+$|^[\d]+- | [\d]+- | [\d]+-$|^[\d]+ - | [\d]+ - | [\d]+ -$|^-[\d]+ | -[\d]+ | -[\d]+$|^- [\d]+ | - [\d]+ | - [\d]+$|^[A-Z]{1}-[A-Z]{1} | [A-Z]{1}-[A-Z]{1} | [A-Z]{1}-[A-Z]{1}$|^[A-Z]{1} - [A-Z]{1} | [A-Z]{1} - [A-Z]{1} | [A-Z]{1} - [A-Z]{1}$|^[A-Z]{1} -[A-Z]{1} | [A-Z]{1} -[A-Z]{1} | [A-Z]{1} -[A-Z]{1}$|^[A-Z]{1}- [A-Z]{1} | [A-Z]{1}- [A-Z]{1} | [A-Z]{1}- [A-Z]{1}$|^[A-Z]{1}- | [A-Z]{1}- | [A-Z]{1}-$|^[A-Z]{1} - | [A-Z]{1} - | [A-Z]{1} -$|^-[A-Z]{1} | -[A-Z]{1} | -[A-Z]{1}$|^- [A-Z]{1} | - [A-Z]{1} | - [A-Z]{1}$|^[\d]+-[A-Z]{1} | [\d]+-[A-Z]{1} | [\d]+-[A-Z]{1}$|^[\d]+ - [A-Z]{1} | [\d]+ - [A-Z]{1} | [\d]+ - [A-Z]{1}$|^[\d]+ -[A-Z]{1} | [\d]+ -[A-Z]{1} | [\d]+ -[A-Z]{1}$|^[\d]+- [A-Z]{1} | [\d]+- [A-Z]{1} | [\d]+- [A-Z]{1}$|^[A-Z]{1}-[\d]+ | [A-Z]{1}-[\d]+ | [A-Z]{1}-[\d]+$|^[A-Z]{1} - [\d]+ | [A-Z]{1} - [\d]+ | [A-Z]{1} - [\d]+$|^[A-Z]{1} -[\d]+ | [A-Z]{1} -[\d]+ | [A-Z]{1} -[\d]+$|^[A-Z]{1}- [\d]+ | [A-Z]{1}- [\d]+ | [A-Z]{1}- [\d]+$|[0-9]+[A-Z]+ ADDN| ADDN [0-9]+-[A-Z]+| ADDN [0-9]+[A-Z]+| ADDN [A-Z]{1} | ADDN [0-9]+| ADDN [A-Z]+-[0-9]+| ADDN [A-Z]+[0-9]+| ADDN [A-Z]$| BLK [0-9]+-[A-Z]+| BLK [A-Z]+-[0-9]+| BLK [0-9]+[A-Z]+| BLK [A-Z]+[0-9]+| BLK [A-Z]{1} | BLK [0-9]+| BLK [A-Z]$| PH [0-9]+-[A-Z]+| PH [A-Z]+-[0-9]+| PH [0-9]+[A-Z]+| PH [A-Z]+[0-9]+| PH [0-9]+| PH[0-9]+| PH [A-Z]{1}| PH [A-Z]$ | REV [0-9]+-[A-Z]+| REV [A-Z]+-[0-9]+| REV [0-9]+[A-Z]+| REV [A-Z]+[0-9]+| REV [0-9]+| REV [A-Z]{1} | REV [A-Z]$| SEC [0-9]+-[A-Z]+| SEC [A-Z]+-[0-9]+| SEC [0-9]+[A-Z]+| SEC [A-Z]+[0-9]+| SEC [0-9]+| SEC [A-Z]{1} | SEC [A-Z]$| LOT [0-9]+-[A-Z]+| LOT [A-Z]+-[0-9]+| LOT [0-9]+[A-Z]+| LOT [A-Z]+[0-9]+| LOT [0-9]+| LOT [A-Z]{1} | LOT [A-Z]$| PAR [0-9]+-[A-Z]+| PAR [A-Z]+-[0-9]+| PAR [0-9]+[A-Z]+| PAR [A-Z]+[0-9]+| PAR [0-9]+| PAR [A-Z]{1} | PAR [A-Z]$| TWP [0-9]+-[A-Z]+| TWP [A-Z]+-[0-9]+| TWP [0-9]+[A-Z]+| TWP [A-Z]+[0-9]+| TWP [0-9]+| TWP [A-Z]{1} | TWP [A-Z]$| TRCT [0-9]+-[A-Z]+| TRCT [A-Z]+-[0-9]+| TRCT [0-9]+[A-Z]+| TRCT [A-Z]+[0-9]+| TRCT [0-9]+| TRCT [A-Z]{1} | TRCT [A-Z]$| AREA [0-9]+-[A-Z]+| AREA [A-Z]+-[0-9]+| AREA [0-9]+[A-Z]+| AREA [A-Z]+[0-9]+| AREA [0-9]+| AREA [A-Z]{1} | AREA [A-Z]$| PART [0-9]+-[A-Z]+| PART [A-Z]+-[0-9]+| PART [0-9]+[A-Z]+| PART [A-Z]+[0-9]+| PART [0-9]+| PART [A-Z]{1} | PART [A-Z]$|^ADDN | ADDN | ADDN$|^BLK | BLK | BLK$|^PH | PH | PH$|^REV | REV | REV$|^SEC | SEC | SEC$|^LOT | LOT | LOT$|^TWP | TWP | TWP$|^TRCT | TRCT | TRCT$|^AREA | AREA | AREA$|^PAR | PAR | PAR$| OF [A-Z]{1} |^OF | OF$| TO [A-Z]{2} | TO [A-Z]{3} |^TO | TO$| AND [0-9]+| AND \w{1} |^AND | AND$|^TO THE | TO THE$|^OF THE | OF THE$| THE$| THE [0-9][A-Z]{2}$|^[0-9]+[A-Z]{2} | [0-9]+[A-Z]{2}$)
Check_All_Again: Tester
    BOOL_OP = OR
    TEST_CLAUSE = CASE_INSENSITIVE_TEST @Value(_SubdName) CONTAINS_REGEX (RE-SUBDIVISION|SUBDIVISION|SUBDV|SUBD|RESUB|RE-SUB| RE SUB |P U D| PUD |AMENDMENT|AMEND|AMEN|PD|UNRECORDED|UNREC|REREC|FINAL PLAN|FINAL PLA|OUTLINE PLAN|PROPOSED| P D |^P D | P D$| PT OF |^PT OF | PT OF$| PART OF |^PART OF | PART OF$| SD |^SD | SD$| S/D |^S/D | S/D$| RES |^RES | RES$|\d+-[A-Z]+ & \d+-[A-Z]+|[A-Z]+-\d+ & [A-Z]+-\d+|\d+[A-Z]+ & \d+[A-Z]+|[A-Z]+\d+ & [A-Z]+\d+|\d+ & \d+| [A-Z] & [A-Z] |\d+-[A-Z]+&\d+-[A-Z]+|[A-Z]+-\d+&[A-Z]+-\d+|\d+[A-Z]+&\d+[A-Z]+|[A-Z]+\d+&[A-Z]+\d+|\d+&\d+| [A-Z]&[A-Z] |\d+-[A-Z]+& \d+-[A-Z]+|[A-Z]+-\d+& [A-Z]+-\d+|\d+[A-Z]+& \d+[A-Z]+|[A-Z]+\d+& [A-Z]+\d+|\d+& \d+| [A-Z]& [A-Z] |\d+-[A-Z]+ &\d+-[A-Z]+|[A-Z]+-\d+ &[A-Z]+-\d+|\d+[A-Z]+ &\d+[A-Z]+|[A-Z]+\d+ &[A-Z]+\d+|\d+ &\d+| [A-Z] &[A-Z] | [A-Z]{1} & [A-Z]{1} |^[A-Z]{1} & [A-Z]{1} | [A-Z]{1} & [A-Z]{1} | [A-Z]{1} & [A-Z]{1}$|^[A-Z]{1}& [A-Z]{1} | [A-Z]{1}& [A-Z]{1} | [A-Z]{1}& [A-Z]{1}$|^[A-Z]{1} &[A-Z]{1} | [A-Z]{1} &[A-Z]{1} | [A-Z]{1} &[A-Z]{1}$|^[A-Z]{1}&[A-Z]{1} | [A-Z]{1}&[A-Z]{1} | [A-Z]{1}&[A-Z]{1}$|^[\d]+-[\d]+ | [\d]+-[\d]+ | [\d]+-[\d]+$|^[\d]+ - [\d]+ | [\d]+ - [\d]+ | [\d]+ - [\d]+$|^[\d]+ -[\d]+ | [\d]+ -[\d]+ | [\d]+ -[\d]+$|^[\d]+- [\d]+ | [\d]+- [\d]+ | [\d]+- [\d]+$|^[\d]+- | [\d]+- | [\d]+-$|^[\d]+ - | [\d]+ - | [\d]+ -$|^-[\d]+ | -[\d]+ | -[\d]+$|^- [\d]+ | - [\d]+ | - [\d]+$|^[A-Z]{1}-[A-Z]{1} | [A-Z]{1}-[A-Z]{1} | [A-Z]{1}-[A-Z]{1}$|^[A-Z]{1} - [A-Z]{1} | [A-Z]{1} - [A-Z]{1} | [A-Z]{1} - [A-Z]{1}$|^[A-Z]{1} -[A-Z]{1} | [A-Z]{1} -[A-Z]{1} | [A-Z]{1} -[A-Z]{1}$|^[A-Z]{1}- [A-Z]{1} | [A-Z]{1}- [A-Z]{1} | [A-Z]{1}- [A-Z]{1}$|^[A-Z]{1}- | [A-Z]{1}- | [A-Z]{1}-$|^[A-Z]{1} - | [A-Z]{1} - | [A-Z]{1} -$|^-[A-Z]{1} | -[A-Z]{1} | -[A-Z]{1}$|^- [A-Z]{1} | - [A-Z]{1} | - [A-Z]{1}$|^[\d]+-[A-Z]{1} | [\d]+-[A-Z]{1} | [\d]+-[A-Z]{1}$|^[\d]+ - [A-Z]{1} | [\d]+ - [A-Z]{1} | [\d]+ - [A-Z]{1}$|^[\d]+ -[A-Z]{1} | [\d]+ -[A-Z]{1} | [\d]+ -[A-Z]{1}$|^[\d]+- [A-Z]{1} | [\d]+- [A-Z]{1} | [\d]+- [A-Z]{1}$|^[A-Z]{1}-[\d]+ | [A-Z]{1}-[\d]+ | [A-Z]{1}-[\d]+$|^[A-Z]{1} - [\d]+ | [A-Z]{1} - [\d]+ | [A-Z]{1} - [\d]+$|^[A-Z]{1} -[\d]+ | [A-Z]{1} -[\d]+ | [A-Z]{1} -[\d]+$|^[A-Z]{1}- [\d]+ | [A-Z]{1}- [\d]+ | [A-Z]{1}- [\d]+$|[0-9]+[A-Z]+ ADDN| ADDN [0-9]+-[A-Z]+| ADDN [0-9]+[A-Z]+| ADDN [A-Z]{1} | ADDN [0-9]+| ADDN [A-Z]+-[0-9]+| ADDN [A-Z]+[0-9]+| ADDN [A-Z]$| BLK [0-9]+-[A-Z]+| BLK [A-Z]+-[0-9]+| BLK [0-9]+[A-Z]+| BLK [A-Z]+[0-9]+| BLK [A-Z]{1} | BLK [0-9]+| BLK [A-Z]$| PH [0-9]+-[A-Z]+| PH [A-Z]+-[0-9]+| PH [0-9]+[A-Z]+| PH [A-Z]+[0-9]+| PH [0-9]+| PH[0-9]+| PH [A-Z]{1}| PH [A-Z]$ | REV [0-9]+-[A-Z]+| REV [A-Z]+-[0-9]+| REV [0-9]+[A-Z]+| REV [A-Z]+[0-9]+| REV [0-9]+| REV [A-Z]{1} | REV [A-Z]$| SEC [0-9]+-[A-Z]+| SEC [A-Z]+-[0-9]+| SEC [0-9]+[A-Z]+| SEC [A-Z]+[0-9]+| SEC [0-9]+| SEC [A-Z]{1} | SEC [A-Z]$| LOT [0-9]+-[A-Z]+| LOT [A-Z]+-[0-9]+| LOT [0-9]+[A-Z]+| LOT [A-Z]+[0-9]+| LOT [0-9]+| LOT [A-Z]{1} | LOT [A-Z]$| PAR [0-9]+-[A-Z]+| PAR [A-Z]+-[0-9]+| PAR [0-9]+[A-Z]+| PAR [A-Z]+[0-9]+| PAR [0-9]+| PAR [A-Z]{1} | PAR [A-Z]$| TWP [0-9]+-[A-Z]+| TWP [A-Z]+-[0-9]+| TWP [0-9]+[A-Z]+| TWP [A-Z]+[0-9]+| TWP [0-9]+| TWP [A-Z]{1} | TWP [A-Z]$| TRCT [0-9]+-[A-Z]+| TRCT [A-Z]+-[0-9]+| TRCT [0-9]+[A-Z]+| TRCT [A-Z]+[0-9]+| TRCT [0-9]+| TRCT [A-Z]{1} | TRCT [A-Z]$| AREA [0-9]+-[A-Z]+| AREA [A-Z]+-[0-9]+| AREA [0-9]+[A-Z]+| AREA [A-Z]+[0-9]+| AREA [0-9]+| AREA [A-Z]{1} | AREA [A-Z]$| PART [0-9]+-[A-Z]+| PART [A-Z]+-[0-9]+| PART [0-9]+[A-Z]+| PART [A-Z]+[0-9]+| PART [0-9]+| PART [A-Z]{1} | PART [A-Z]$|^ADDN | ADDN | ADDN$|^BLK | BLK | BLK$|^PH | PH | PH$|^REV | REV | REV$|^SEC | SEC | SEC$|^LOT | LOT | LOT$|^TWP | TWP | TWP$|^TRCT | TRCT | TRCT$|^AREA | AREA | AREA$|^PAR | PAR | PAR$| OF [A-Z]{1} |^OF | OF$| TO [A-Z]{2} | TO [A-Z]{3} |^TO | TO$| AND [0-9]+| AND \w{1} |^AND | AND$|^TO THE | TO THE$|^OF THE | OF THE$| THE$| THE [0-9][A-Z]{2}$|^[0-9]+[A-Z]{2} | [0-9]+[A-Z]{2}$)
    TEST_MODE = CASE_INSENSITIVE_TEST
    PASSED -> Keywords_Loop (output)
    FAILED -> Check_for_spaces_again

Bookmark: To Keywords Loop
Keywords_Loop (output)

Bookmark: Check for spaces again
Check_for_spaces_again: Tester
    BOOL_OP = OR
    TEST_CLAUSE:
      CASE_INSENSITIVE_TEST @Value(_SubdName) CONTAINS_REGEX
      CASE_INSENSITIVE_TEST @Value(_ParcelID) CONTAINS_REGEX
    TEST_MODE = CASE_INSENSITIVE_TEST
    PASSED -> Init_Space (output)
    FAILED -> Last_Trimmer
Note: Do one last trim on the ends
Last_Trimmer: AttributeTrimmer
    SRC_ATTRS = _SubdName
    TRIM_CHARS = " "
    TRIM_TO_NONE = Yes
    TRIM_TYPE = Both
    -> Output (output)

Bookmark: Initial Space Loop
Init_Space (output)

Bookmark: Remnant Phrases Loop
Remant_Keyphrases (output)
